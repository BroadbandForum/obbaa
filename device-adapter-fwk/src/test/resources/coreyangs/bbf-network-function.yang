module bbf-network-function {
  yang-version 1.1;
  namespace "urn:bbf:yang:bbf-network-function";
  prefix bbf-nf;

  import bbf-yang-types {
    prefix bbf-yang;
  }

  import bbf-network-function-types {
    prefix bbf-nf-types;
  }

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     WA Director: George Dobrowski, Morris Creek Consulting

     WA Director: Bruno Cornaglia, Vodafone";
  description
    "This module contains a collection of YANG definitions needed
     for entities that manage or monitor network functions.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2021-08-19 {
    description
      "Initial revision.";
    reference
      "TBD";
  }

  // Groupings

  // Virtual Network Function
  grouping virtual-network-function {
    description
      "A Virtual Network Function (VNF) that defines the type of VNF
       not the instance of a type of VNF.";
    leaf name {
      type bbf-yang:string-ascii64;
      description 
        "The name of the VNF.";
    }
    leaf vendor {
      type bbf-yang:string-ascii64;
      description 
        "The vendor of the VNF.";
    }
    leaf software-version {
      type bbf-yang:string-ascii64;
      description 
        "The software version of VNF.";
    }
    leaf network-function-type {
      type identityref {
        base "bbf-nf-types:nf-type";
      }
      description 
        "The type of the VNF within the solution context.
         For example: ONU-Management-Proxy, vOMCI-function, 
         vOMCI-Proxy";
    }
  }

  // Virtual Network Functions
  grouping virtual-network-functions {
    description
      "The VNF types (not instances) known to this entity.";
    list virtual-network-function {
      key "name";
      description "VNF types (not instances) known to this entity.";
      uses virtual-network-function;
    }
  }

  // Virtual Network Function Instance
  grouping virtual-network-function-instance {
    description
      "The definition of a VNF instance.";
    leaf name {
      type bbf-yang:string-ascii64;
      description "The name of the VNF instance.";
    }
    leaf virtual-network-function {
      type bbf-yang:string-ascii64;
      description 
        "The name of the VNF associated with this instance.";
    }
  }

  // Virtual Network Function Instances
  grouping virtual-network-function-instances {
    description
      "Instances of VNFs.";
    list virtual-network-function-instance {
      key "name";
      description 
        "The VNF instances known to this entity";
      uses virtual-network-function-instance;
      
    }
  }

  // Network function Link
  grouping network-function-link {
    description
      "Network function endpoints that comprise a link.";
    leaf name {
      type string;
      description 
        "The name of the network function link.";
    }
    list endpoint {
      key "function-name endpoint-name";
      description "Network function endpoint.";
      leaf function-name {
        type bbf-yang:string-ascii64;
        description 
          "The name of the instance of the network function.
           If the function is a PNF, then this value is the 
           device identifier of the PNF.";
      }
      leaf endpoint-name {
        type bbf-yang:string-ascii64;
        description 
          "The name of the network function endpoint.";
      }
    }
  }

  // Network function Links
  grouping network-function-links {
    description
      "List of network function endpoints that comprise a link.";
    list network-function-link {
      key "name";
      description
        "List of network function links.";
      uses network-function-link;
    }
  }

}
