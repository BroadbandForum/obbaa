module bbf-obbaa-onu-management {
    yang-version 1.1;
    namespace "urn:bbf:yang:obbaa:onu-management";
    prefix baa-onu-management;

    import bbf-obbaa-network-manager {
      prefix baa-network-manager;
    }
    
    import bbf-xpon-types {
      prefix bbf-xpon-types;
    }
    
    import bbf-xpon-onu-types {
      prefix bbf-xpon-onu-types;
    }
    
    import bbf-voltmf-entity{
      prefix bbf-voltmf-entity;
    }
    import bbf-voltmf-message-monitor {
      prefix bbf-voltmf-msg-mon;
    }
    
    import bbf-obbaa-xpon-onu-types {
      prefix baa-xpon-onu-types;
    }
    
    import bbf-yang-types {
       prefix bbf-yang;
    }

    import bbf-vomci-types {
       prefix bbf-vomcit;
    }
    
    organization
      "Broadband Forum <https://www.broadband-forum.org>";

    contact
      "Comments or questions about this Broadband Forum YANG module
       should be directed to <mailto:obbaa-leaders@broadband-forum.org>.
      ";

    description
      "This module contains a collection of YANG definitions for 
       the management of ONUs. This module is applicable to the device 
       aggregation function of OB-BAA.
       
       Copyright 2020-2021 Broadband Forum
       
       Licensed under the Apache License, Version 2.0 (the \"License\");
       you may not use this file except in compliance with the License.
       You may obtain a copy of the License at
       
       http://www.apache.org/licenses/LICENSE-2.0
       Unless required by applicable law or agreed to in writing, software
       distributed under the License is distributed on an \"AS IS\" BASIS,
       WITHOUT WARRANTIES OR CONDITIONS OF ANY KIND, either express or implied.
       See the License for the specific language governing permissions and
       limitations under the License. 
      ";
    
    revision 2021-11-10 {
       description
         "Changes to support ONU Authentication in OB-BAA Rel 5.0.0.";
       reference
          "https://obbaa.broadband-forum.org/";
    }
    
    revision 2021-04-21 {
       description
         "Changes to support vOMCI function enhancements in OB-BAA Rel 4.1.0.";
       reference
          "https://obbaa.broadband-forum.org/";
    }
    
    revision 2020-07-15 {
      description
        "Initial revision.";
      reference
        "broadband_forum";
    }

    grouping onu-state-general-parameters {
       description 
          "General ONU state parameters.";
       
       leaf detected-serial-number {
          type bbf-xpon-types:onu-serial-number;
          description
            "The serial number of the Optical Network Unit (ONU).";
          reference
            "ITU-T G.984.3, clause 9.2.4.1
             ITU-T G.987.3, clause 11.3.3.2
             ITU-T G.9807.1, clauses C11.2.6.1, C11.2.6.2 and
             C11.3.4.1
             ITU-T G.989.3, clauses 11.2.6.1, 11.2.6.2 and 11.3.4.1.";
       }
       
       leaf detected-registration-id {
          type bbf-xpon-types:onu-registration-id;
          description
            "The registration ID value which the Optical Line
             Termination (OLT) has received from the Optical Network
             Unit (ONU). This leaf is not present if the ONU has not
             provided any registration ID to the OLT. Registration ID
             may be useful in identifying a particular ONU installed
             at a particular location. Each octet is represented as 2
             hexadecimal characters, therefore the leaf must contain an
             even number of characters. For ITU-T G.984.3, the leaf
             can only be up to 20 octets long (refer to 'password'),
             for ITU-T G.987.3, ITU-T G.9807.3 and ITU-T G.989.3
             the leaf can be up to 72 octets long.";
          reference
            "ITU-T G.984.3 clause 9.2.4.2
             ITU-T G.987.3 clause 11.3.4.2
             ITU-T G.9807.3 clause C.11.3.4.2
             ITU-T G.989.3 clause 11.3.4.2";
       }
    }
    
    grouping onu-state-attachment-point-parameters {
       description 
          "Defines state parameters regarding an ONU's attachment point";
       
       leaf olt-name {
          type string;
          mandatory true;
          description
            "A reference to the OLT where the ONU is attached";
       }
        
       leaf channel-termination-name {
          type string;
          mandatory true;
          description
            "The local name of the channel termination in the OLT where the ONU is attached";
       }
        
       leaf onu-id {
          type bbf-xpon-types:onu-id;
          description
            "This is the ITU-T Transmission Convergence (TC) layer ONU-ID
             identifier which the Optical Line Termination (OLT) has
             assigned to the Optical Network Unit (ONU) during the ONU's
             activation using the Assign_ONU-ID PLOAM message. It
             identifies an ONU on a channel group and is unique on a
             channel group.";
          reference
            "ITU-T G.984.3 clause 5.5.2
             ITU-T G.987.3 clause 6.4.2
             ITU-T G.9807.1 clause C.6.1.5.6
             ITU-T G.989.3 clause 6.1.5.6";
       }
    }
    
    grouping onu-auth-parameters {
       description 
          "Parameters related to ONU authentication.";
       
       leaf v-ani-name {
          type string;
          description
            "The virtual Access Network Interface (vANI) corresponding to
             this Optical Network Unit (ONU). This leaf is not present if the 
             OLT could not determine a vANI corresponding to the ONU.";
       }
        
       leaf olt-local-onu-name {
          type string;
          description
            "The local name of the ONU as known in the Optical Line Termination 
            (OLT). This leaf would typically reflect the onu-name configured 
            in the corresponding virtual Access Network Interface (vANI). This
            leaf is not present if the OLT could not determine a vANI
            corresponding to the ONU.";
       }
    }
    
    augment '/baa-network-manager:network-manager/baa-network-manager:managed-devices/'
          + 'baa-network-manager:device/baa-network-manager:device-management' {
       when
           "/baa-network-manager:network-manager/baa-network-manager:managed-devices/"
         + "baa-network-manager:device/baa-network-manager:device-management/"
         + "baa-network-manager:type = 'ONU'";
       
         description
           "Additional information for a ONU";
         
         container onu-config-info {
           description 
             "ONU management info";
           
           leaf vendor-name {
              type string;
              description "The ONU vendor";
           }
           
           leaf expected-serial-number {
             type bbf-xpon-types:onu-serial-number;
             description
               "The expected serial number for this ONU.
                The serial number is unique for each ONU.
                It contains the vendor ID and vendor specific serial
                number. The first four bytes are an ASCII-encoded
                vendor ID four letter mnemonic. The second four bytes
                are a binary encoded serial number, under the control
                of the ONU vendor.";
             reference
               "ITU-T G.984.3, clause 9.2.4.1
               ITU-T G.987.3, clause 11.3.3.2
               ITU-T G.9807.1, clauses C11.2.6.1, C11.2.6.2 and C11.3.4.1
               ITU-T G.989.3, clauses 11.2.6.1, 11.2.6.2 and 11.3.4.1.";
           }
           
           leaf expected-registration-id {
              type bbf-xpon-types:onu-registration-id;
              default "";
              description
                "A string that has been assigned to the subscriber
                 on the management level, entered into and stored
                 in non-volatile storage at the ONU. Registration ID may be
                 useful in identifying a particular ONU installed at a
                 particular location. Each octet is represented as 2
                 hexadecimal characters, therefore the leaf must contain an
                 even number of characters.
                 For ITU-T G.984.3, the leaf can only be up to 20 characters
                 long (refer to 'password' 10 bytes long).
                 For ITU-T G.987.3, ITU-T G.9807.3 and ITU-T G.989.3 the
                 leaf can be up to 72 characters long (refer to
                 'registration id' 36 bytes long).";
              reference
                "ITU-T G.984.3 clause 9.2.4.2
                 ITU-T G.987.3 clause 11.3.4.2
                 ITU-T G.9807.3 clause C.11.3.4.2
                 ITU-T G.989.3 clause 11.3.4.2";
           }
           
           leaf xpon-technology {
              type identityref {
                 base bbf-xpon-types:channel-pair-type-base;
               }
               description
                 "Represents the type of channel termination (e.g.
                  TWDM NG-PON2, PtP NG-PON2, XGS-PON, XG-PON, G-PON).";
           }
           
           leaf planned-onu-management-mode {
              type identityref {
                base baa-xpon-onu-types:onu-management-config-base;
              }
              default baa-xpon-onu-types:use-vomci;
              description
                 "Indicates whether embedded OMCI (eOMCI) or vOMCI is to be 
                 used, when it is not configured explicity for a specified 
                 expected attachment point.";
           }

           
           container expected-attachment-points {
              description 
                 "Container for holding attachment point information.";
           
              leaf list-type {                
                 type enumeration {
                    enum strict {
                       description
                          "The ONU is only permitted in the attachment points
                          specified in the 'expected-attachment-point' list.
                          Other attachments are not allowed.";
                    }
                    enum allow-any {
                       description
                          "The ONU is permitted in any attachment point. In
                          this case, the 'expected-attachment-point' list 
                          is used to specify configuration which is 
                          specific for a given attachment point.";
                    }
                 }
                 default allow-any;
                 description 
                    "This leaf defines how the 'expected-attachment-point'
                    list must be interpreted.";
              }
              
              list expected-attachment-point {
                 key "name";
                 
                 description
                   "The list of allowed attachment points for an ONU.";
                 
                 leaf name {
                    type string;
                    description
                       "Attachment point name.";
                 }
                 
                 leaf olt-name {
                   type leafref {
                       path '/baa-network-manager:network-manager/baa-network-manager:managed-devices/baa-network-manager:device/baa-network-manager:name';
                   }
                   mandatory true;
                   description
                     "A reference to the OLT where the ONU is expected";
                 }
                 
                 leaf channel-partition-name {
                   type string;                
                   description
                     "The local name of the channel-partition in the OLT where the
                      ONU is expected. If not specified, the ONU will be allowed on 
                      any channel partition of the OLT.";
                 }
                 
                 leaf planned-onu-management-mode-in-this-olt { 
                    type identityref {
                      base baa-xpon-onu-types:onu-management-config-base;
                    }
                    description
                      "When configured, indicated whether eOMCI or vOMCI 
                       must be used for this ONU in this OLT. 
                       When not configured, the 'planned-onu-management-mode' 
                       global YANG leaf per ONU will determine whether eOMCI
                       or vOMCI must be used for this ONU, independent of
                       the OLT on which it is showing-up.";
                 }
              }
           }
           
           container vomci-onu-management {
              description
                "Configuration and state date needed to manage ONU's via 
                 vOMCI.";
              
              //Should include the onu-management-chain, but at the time of 
              //this change, the onu-management-chain definition makes it
              //unusable. A workaround was applied to the local copy of
              //bbf-voltmf-entity.
              uses bbf-voltmf-entity:vomci-onu-config;
             
              list onu-management-chain {
                 key "nf-type nf-name";
                 ordered-by user;
                  
                 description
                    "The ordered list of ONU Management Proxy, vOMCI function, 
                     vOMCI Proxy and OLT entities to use for this ONU's 
                     management. When the ONU Management Proxy is not deployed, 
                     the list is ordered from the vOMCI function to the OLT 
                     inclusive. If the vomci-function choice is used for the 
                     vomci-function-selection then list contains the vOMCI 
                     function instance. When the ONU Management Proxy is 
                     deployed, the list is ordered with the ONU Management Proxy
                      and then the OLT.";
                 
                 leaf nf-type {
                   type bbf-vomcit:vomci-entity-type;
                   description 
                      "The type of function: ONU Management Proxy, 
                      vOMCI function, vOMCI Proxy or OLT.";
                 }
                 leaf nf-name {                    
                   type bbf-yang:string-ascii64;
                   description 
                      "Reference to the function instance. In the OB-BAA case,
                      it will reference a device in the device list or a 
                      an instance in the configured network function list. In 
                      the future, the network functions may be discovered";
                 }
              }
           }
       }
    }
    
    
    
    augment '/baa-network-manager:network-manager/baa-network-manager:managed-devices/'
       + 'baa-network-manager:device/baa-network-manager:device-management/'
       + 'baa-network-manager:device-state' {
    when
        "/baa-network-manager:network-manager/baa-network-manager:managed-devices/"
      + "baa-network-manager:device/baa-network-manager:device-management/"
      + "baa-network-manager:type = 'ONU'";
      
      description
        "Additional information for a ONU";
      
      container onu-state-info {
        description 
          "Information about an ONU. These parameters are only available when
           the ONU is authenticated";
        
        leaf onu-state {
          type identityref {
            base bbf-xpon-onu-types:onu-presence-state-base;
          }
          mandatory true;
          description
            "This leaf presents the state of the ONU, as reported by the OLT.
             The most specific applicable identity should be provided as
             value.";
        }
        
        leaf determined-onu-management-mode {
           type identityref {
             base baa-xpon-onu-types:onu-management-state-base;
           }
           description
             "This YANG leaf may only be present when the corresponding 
              Optical Network Unit (ONU) is present on a channel 
              termination and has been successfully authenticated. 
              It provides the ONU management mode as best determined  
              by the Optical Line Termination (OLT), ideally  
              discriminating between eOMCI and vOMCI."; 
           reference
             "WT-489";
        }
        
        uses onu-state-general-parameters;
        
        leaf vendor-id {
          type string {
              pattern '[a-zA-Z]{4}';
            }
            description "This attribute identifies the vendor of the ONU.";
            
            reference
              "ITU-T G.988, clause 9.1.1";
        }
        
        leaf equipment-id {
          type string {
            pattern '[a-zA-Z]{4}[0-9a-fA-F]{20}';
          }
          description "This attribute may be used to identify the specific type of ONU.";
          
          reference
            "ITU-T G.988, clause 9.1.2";
        }
        
        container attachment-point {
           description
             "The current ONU attachment point";
           
           uses onu-state-attachment-point-parameters;
           
           uses onu-auth-parameters;
        }
        
        container software-images {
          description
             "Software image information.";
          list software-image{ 
            key "id";
            description
               "Software image list";
            
            leaf id {
               type uint8 {
                  range "0..1";
               }
               description
                 "The software image instance Id.";
               reference
                 "ITU-T G.988, clause 9.1.4";
            }
               
            leaf version {
              type string;
              description 
                "The software version";
              reference
                 "ITU-T G.988, clause 9.1.4";
              
            }
            
            leaf is-committed {
              type boolean;
              mandatory true;
              description
                "Reports whether the associated software revision is
                 committed ('true') or uncommitted ('false').";
              reference
                "ITU-T G.988, clause 9.1.4";
            }
            
            leaf is-active {
              type boolean;
              mandatory true;
              description
                "Reports whether the associated software revision is
                 active ('true') or inactive ('false').";
              reference
                "ITU-T G.988, clause 9.1.4";
            }
            
            leaf is-valid {
              type boolean;
              mandatory true;
              description
                "Reports whether the stored software revision is
                 valid ('true') or invalid ('false').";
              reference
                "ITU-T G.988, clause 9.1.4";
            }
            
            leaf product-code {
              type string;
              description
                "Reports the product code information of the software
                 revision.";
              reference
                "ITU-T G.988, clause 9.1.4";
            }
            leaf hash {
              type string;
              description
                "Reports the hash value calculated by the corresponding
                 hash function at completion of the end download of the
                 software revision.";
              reference
                "ITU-T G.988, clause 9.1.4";
            }
            
           }
          }
          container voltmf-msg-data {
             description
                "This container contains the counters for the vOLTMF messages
                 sent between the vOLTMF and vOMCI funciton.";
   
             uses bbf-voltmf-msg-mon:voltmf-msg-statistics-grouping;
          }
        
        
        }
        
    }
    

    augment '/baa-network-manager:network-manager/baa-network-manager:managed-devices/'
      + 'baa-network-manager:device/baa-network-manager:device-management/' 
      + 'baa-onu-management:onu-config-info/baa-onu-management:vomci-onu-management'
      {
        description 
           "Additions specific to vOMCI ONU management.";
       
        container network-function-links {
          
          description
            "Holds a list of links and endpoint names associated to the management 
            chain of the ONU when discovery is not possible or not wanted. The 
            endpoint names are needed by the vOLTMF when sending the 
            'set-onu-communication' action to the vOMCI function and vOMCI
            proxy.";
          
          list network-function-link {
            key name;
            description 
              "List of network functions links between two network functions.";
            
            leaf name {
               type string;
               description
                  "Link name.";
            }
            container termination-point-a {
               description 
                  "Source network function.";
               
               leaf function-name {
                  //workaround, should be a leafref to the onu-management-chain
                  type string;
                  mandatory true;
                  description
                    "Network function name.";
               }
               leaf local-endpoint-name {
                  type string;
                  mandatory true;
                  description 
                    "The local endpoint name.";
               }  
            }
            container termination-point-b {
               description 
                  "Destination network function.";
               
               leaf function-name {
                  //workaround, should be a leafref to the onu-management-chain
                  type string;
                  mandatory true;
                  description
                    "Network function name.";
               }
               leaf local-endpoint-name {
                  type string;
                  mandatory true;
                  description 
                    "The local endpoint name.";
               }  
            }
            
          }
        }
      
    }
    
    // Notifications
    notification onu-authentication-report-notification {       
       description 
          "A notification to report ONU authentication events for a given 
          ONU.";
       
       leaf onu-authentication-status {
          type identityref {
             base baa-xpon-onu-types:onu-authentication-notification-base;
          }
          mandatory true;
          description 
             "Identifies the authentication event.";
       }
       
       uses onu-state-attachment-point-parameters;

       uses onu-state-general-parameters;

       uses onu-auth-parameters;
       
       leaf onu-name {
          type string;
          description
            "The name of the ONU in the BAA device list if it was possible 
             for the BAA to associate it to a particular device instance.";
       }
       
    }

}
