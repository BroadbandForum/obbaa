module bbf-kafka-agent {
  yang-version 1.1;
  namespace "urn:bbf:yang:bbf-kafka-agent";
  prefix bbf-kafkaa;

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     PS Leader:   Yves Hertoghs, VMWare

     WA Director: George Dobrowski, Morris Creek Consulting

     WA Director: Bruno Cornaglia, Vodafone";
  description
    "This module contains a collection of YANG definitions needed to
     communicate with Kafka brokers as an agent.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2021-02-19 {
    description
      "Initial revision.";
    reference
      "TR-451: Section 5.5.3.1 Message Transfer Using Kafka";
  }

  // Features
  feature publication-supported {
    description
      "Indicates that the agent supports publication 
       of messages to the broker on specific topics.";
  }

  feature consumption-supported {
    description
      "Indicates that the agent supports consumption 
       of message from the broker on specific topics.";
  }
 
  // Groupings
  grouping kafka-topic-parameters {
    description
    "A reusable grouping for configuring Kafka topics.";
    leaf name {
      type string;
      description
        "The name of the topic.";
    }
    leaf purpose {
      type string;
      description
        "The purpose of the topic (e.g., VOMCI_NOTIFICATION,
         VOMCI_REQUEST, VOMCI_RESPONSE).";
    }
    leaf partition {
      type string;
      description
        "For topics that are partitioned, the partition used for
         production and consumption.";
    }
  }
  
  grouping kafka-agent-grouping {
    description
      "A reusable grouping for configuring a Kafka agent.

       Note that this grouping uses fairly typical descendent
       node names such that a stack of 'uses' statements will
       have name conflicts.  It is intended that the consuming
       data model will resolve the issue (e.g., by wrapping
       the 'uses' statement in a container called
       'kafka-agent-parameters').  This model purposely does
       not do this itself so as to provide maximum flexibility
       to consuming models.";

    leaf client-id {
        type string;
        description
          "The identifier that the client/consumer (agent) uses 
           to identify the source of a message.";
    }

    container publication-parameters{
      if-feature "bbf-kafkaa:publication-supported";
      description
        "The Kafka agent publication properties.";
      list topic {
        key name;
        description
          "The topics the agent will publish.";
        uses kafka-topic-parameters;
      }
    }
    container consumption-parameters{
      if-feature "bbf-kafkaa:consumption-supported";
      description
        "The Kafka agent consumption properties.";

      leaf group-id {
          type string;
          description
            "The identifier that the group that the consumer can 
             participate.";
      }

      list topics {
        key name;
        description
          "The topics the agent will consume.";
        uses kafka-topic-parameters;
      }
    }
  }
}
