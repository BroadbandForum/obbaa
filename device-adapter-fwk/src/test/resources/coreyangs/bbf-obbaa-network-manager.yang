module bbf-obbaa-network-manager {
    yang-version 1.1;
    namespace "urn:bbf:yang:obbaa:network-manager";
    prefix baa-network-manager;

    import ietf-inet-types {
        prefix inet;
    }
    import ietf-yang-types {
        prefix yang;
    }
    import ietf-yang-schema-mount {
        prefix yangmnt;
    }
    import ietf-yang-library {
        prefix yanglib;
        revision-date 2016-06-21;
    }
    import bbf-network-function-client {
       prefix bbf-nfc;
    }     
    import bbf-network-function-server {
       prefix bbf-nfs;
    }
    import bbf-network-function-types {
       prefix bbf-nf-types;
    }
     
    
    organization
      "Broadband Forum <https://www.broadband-forum.org>";

    contact
      "Comments or questions about this Broadband Forum YANG module
       should be directed to <mailto:obbaa-leaders@broadband-forum.org>.
      ";

    description
      "This module contains a collection of YANG definitions for supporting network management.
              
       Copyright 2018-2019 Broadband Forum
       
       Licensed under the Apache License, Version 2.0 (the \"License\");
       you may not use this file except in compliance with the License.
       You may obtain a copy of the License at
       
       http://www.apache.org/licenses/LICENSE-2.0
       Unless required by applicable law or agreed to in writing, software
       distributed under the License is distributed on an \"AS IS\" BASIS,
       WITHOUT WARRANTIES OR CONDITIONS OF ANY KIND, either express or implied.
       See the License for the specific language governing permissions and
       limitations under the License.
      ";

    revision 2021-02-01 {
       description
         "Added support for vOMCI function management.";
    }
     
    revision 2020-07-23 {
        description
          "Added support for vOMCI managed ONUs.";
    }
    
    revision 2020-02-19 {
        description
          "Added support for SNMP connection model Authentication.";
    }

    revision 2018-05-07 {
        description
          "Initial revision.";
        reference
          "broadband_forum";
    }

    //  Features
    feature nf-client-supported {
      description
        "Indicates that client connectivity to network function's
         endpoints are supported.";
    }

    feature nf-server-supported {
      description
        "Indicates that server connectivity for network function's
         endpoints are supported.";
    }
    
    grouping connection-grouping {
        description
          "Information about the connection for the device managed by BAA.";
        leaf connection-model {
            type enumeration {
                enum call-home;
                enum direct;
                enum snmp;
                enum mediated-session;
            }
            description
              "whether the connection is call-home/direct/snmp 
               or a session mediated through another device.";
        }
        choice protocol {
            mandatory true;
            description
                "Informations about the connection for the device managed by BAA.";
            container password-auth {
                when "../connection-model = 'direct'";
                description
                    "Informations when a device managed by BAA on direct way.When user
                    create a device by BAA, the infomations bellow would be mandatory.";
                container authentication {
                    description
                        "Mandatory informations when BAA try to create a device.";
                    leaf address {
                        type inet:ip-address;
                        mandatory true;
                        description
                          "Device IP address.";
                    }
                    leaf management-port {
                        type uint32;
                        description
                          "The management port of the device.";
                    }
                    leaf user-name {
                        type string;
                        description
                          "The user name of the device.";
                    }
                    leaf password {
                        type string;
                        description
                          "The password of the user.";
                    }
                }
            }
            container snmp-auth {
                when "../connection-model = 'snmp'";
                description
                    "Information when a device managed by BAA on SNMP. When user
                    creates a device by BAA, the information below would be mandatory.";
                container snmp-authentication {
                    description
                        "Mandatory information when BAA tries to create an SNMP device.";
                    leaf address {
                        type inet:ip-address;
                        mandatory true;
                        description
                          "Device IP address.";
                    }
                    leaf agent-port {
                        type inet:port-number;
                        description
                          "The snmp port of the device.";
                    }
                    leaf trap-port {
                        type inet:port-number;
                        description
                          "The snmp trap listening port of manager.";
                    }
                    leaf snmp-version {
                        type enumeration {
                          enum v1;
                          enum v2c;
                          enum v3;
                        }
                        description
                          "SNMP version";
                    }
                    choice auth-info {
                      leaf community-string {
                          when "(../snmp-version = 'v1') or
                               (../snmp-version = 'v2c')";
                          type string;
                          description
                            "SNMP community string";
                      }
                      container snmpv3-auth {
                        when "../snmp-version = 'v3'";
                        leaf user-name {
                          type string;
                          description
                            "SNMP V3 username";
                        }

                        leaf security-level {
                          type enumeration {
                            enum noAuthNoPriv;
                            enum authNoPriv;
                            enum authPriv;
                          }
                          description
                            "Security level";
                        }

                        leaf auth-protocol {
                          when "../security-level != 'noAuthNoPriv'";
                          type enumeration {
                            enum AuthMD5;
                            enum AuthSHA;
                            enum AuthHMAC192SHA256;
                            enum AuthHMAC384SHA512;
                          }
                          description
                            "Authentication protocol";
                        }

                        leaf auth-password {
                          when "../security-level != 'noAuthNoPriv'";
                          type string {
                            length "1..max";
                          }
                          description
                            "Passphrase for authentication protocol";
                        }

                        leaf priv-protocol {
                          when "../security-level = 'authPriv'";
                          type enumeration {
                            enum PrivDES;
                            enum PrivAES;
                            enum PrivAES128;
                            enum PrivAES192;
                            enum PrivAES256;
                            enum Priv3DES;
                          }
                          description
                            "Privacy protocol";
                        }

                        leaf priv-password {
                          when "../security-level = 'authPriv'";
                          type string {
                            length "1..max";
                          }
                          description
                            "Passphrase for privacy protocol";
                        }
                      }
                    }
                }
            }
            leaf duid {
                when "../connection-model = 'call-home'";
                type string {
                    length "1..128";
                }
                description
                  "A globally unique value for a DUID (DHCP Unique Identifier)
                   as defined in RFC 3315.";
            }
            
            leaf mediated-protocol {
                when "../connection-model = 'mediated-session'";
                type enumeration {
                     enum vomci {
                      description
                        "This value applies to vOMCI managed ONUs";
                    }
                }
                description
                  "The protocol being mediated.";
            }
            
        }
    }

    grouping device-details {
        description
          "These four leafs collectively determine one module-set/one adapter.";
        leaf type {
            type string;
            description
              "The type of device. Identifies the type of access node like OLT/ONT/DPU etc";
        }
        leaf interface-version {
            type string;
            description
              "The interface version of the device , which uniquely identifies the yang-modules set & revision supported by the device";
        }
        leaf model {
            type string;
            description
              "The model of device. Identifies the hardware variant of the device.
               Example 4LT/8LT card numbers etc";
        }
        leaf vendor {
            type string;
            description
              "The vendor of device.Eg Nokia/Huawei";
        }
        leaf push-pma-configuration-to-device {
            type boolean;
            default true;
            description
              "By default, push the PMA configuration to the device when the device connects for the first time. This is done since PMA in OB-BAA is the master of configurations. Configure this attribute as false using <edit-config> to turn-off this feature and upload device configuration to PMA.
               When this attribute is set to false, it will be automatically reset to true after the device configuration is successfully uploaded to PMA.";
        }
        leaf is-netconf {
            config false;
            type boolean;
            default true;
            description
              "Specifies if the device is a netconf device or non-netconf device.";
        }
    }

    grouping management-grouping {
        description
            "This grouping contains the information to manage a device.";
        uses device-details;
        container device-connection {
            description
                "Connection infomation of a device.";
            uses connection-grouping;
        }
        container device-state {
            config false;
            description
                "State infomation of a device.";
            leaf configuration-alignment-state {
                type string;
                description
                    "Indicates whether this device was aligned to BAA.";
            }
            container connection-state {
                description
                    "Connection state info of a device.";
                leaf connected {
                    type boolean;
                    description
                      "The connection state of device.";
                }
                leaf connection-creation-time {
                    type yang:date-and-time;
                    description
                      "The time when the device was created.";
                }
                leaf-list device-capability {
                    type string;
                    description
                      "Capabilities of a device.";
                }
            }
        }
    }

    grouping notification-grouping {
        description
          "This grouping contains a notification triggered when the state of
          a device changed.";
        notification device-state-change {
            description
              "Device state changed";
            leaf event {
                type enumeration {
                    enum online;
                    enum offline;
                }
                description
                  "events definition for device state change";
            }
        }
    }
    container network-manager {
        description
          "Infomations about the devices and adapters managed by BAA";
        container managed-devices {
            description
              "The managed devices and device communication settings.";
            list device {
                key "name";
                description
                    "The device list which managed by BAA.";
                leaf name {
                    type string;
                    description
                      "The name of device.";
                }
                container device-management {
                    description
                        "The management informations for a device.";
                    uses management-grouping;
                }
                container device-notification {
                    description
                        "The notification triggered when the device state changed.";
                    uses notification-grouping;
                }
                container root {
                    yangmnt:mount-point "root";
                    description
                      "Root for models supported per device.";
                }
            }
        }
       
        container network-functions-settings
        {
           description
             "Container for network function settings.";
           container nf-client {
              if-feature "nf-client-supported";
              description
                "Client network function configuration.";
              leaf enabled {
                type boolean;
                default "true";
                description
                  "Administratively enable the use of the 
                   client connectivity capability to the 
                   network function.";
              }
              uses bbf-nfc:nf-endpoint-grouping;
           } //nf-client

           container nf-server {
              if-feature "nf-server-supported";
              description
                "Server network function configuration.";
              leaf enabled {
                type boolean;
                default "true";
                description
                  "Administratively enable the use of the 
                   server connectivity capability for connecting 
                   network function.";
              }
              uses bbf-nfs:nf-server-grouping;
            } //nf-server
        }
           
        container network-functions {
           description
             "The network function list.";
           list network-function {
               key "name";
               description
                   "A list of network functions.";
               leaf name {
                   type string;
                   description
                     "The name of the network function.";
               }
               
               leaf type {
                  type identityref {
                     base "bbf-nf-types:vnf-type";
                  }
                  description
                     "The type of the network function (e.g, vomci-function-type, 
                     vomci-proxy-type).";
               }
               
               leaf remote-endpoint-name {
                  type string;
                  description
                    "The remote endpoint name to use for transmitting and
                     receiving messages towards the network function.";
                }
               
               container root{
                   yangmnt:mount-point "root";
                   description
                     "Root for models supported per network function.";
               }
           }
        }
        
        container new-devices {
            config false;
            description
              "This container contains the new devices which connect to BAA.";
            list new-device {
                key "duid";
                description
                    "List of the new devices which trying to connect BAA.";
                leaf duid {
                    type string {
                        length "1..128";
                    }
                    description
                      "A globally unique value for a DUID (DHCP Unique Identifier)
                       as defined in RFC 3315.";
                }
                leaf-list device-capability {
                    type string;
                    description
                      "This list contains the capabilities of a device.";
                }
            }
        }

        container device-adapters {
            config false;
            description
              "This container describe what infomations contains by an adapter.";
            leaf device-adapter-count {
                type string;
                config false;
                description
                  "Total number of device-adapters deployed";
            }
            list device-adapter {
                key "type interface-version model vendor";
                description
                  "List of device-adapters containing yang modules along with supported deviations and features.
                   An device-adapter is uniquely identified by its type, version, model and vendor.";

                uses device-details;

                leaf description {
                    type string;
                    config false;
                    description
                      "Brief description for this adapter.";
                }

                leaf developer {
                    type string;
                    config false;
                    description
                      "Name of the developer for this adapter.";
                }

                leaf revision {
                   type string {
                     pattern '\d{4}-\d{2}-\d{2}';
                   }
                    config false;
                    description
                      "the latest time when the adapter create or modify";
                }

                leaf upload-date {
                  type yang:date-and-time;
                  description
                    "The time when the adapter upload to BAA.";
                }

                leaf in-use {
                    type boolean;
                    description
                      "This node indicates there is whether or not a device was created based on
                       this adapter.";
                }

                container devices-related {
                    when "../in-use = 'true'";
                    description
                      "This container contains a list of devices which created based on this adapter.";
                    leaf device-count {
                        type uint32;
                        description
                          "Total number of devices.";
                    }
                    list device {
                        key "name";
                        description
                          "This list contains all the devices which were created base on the adapter.";
                        leaf name {
                            type leafref {
                                path '/baa-network-manager:network-manager/baa-network-manager:managed-devices/baa-network-manager:device/baa-network-manager:name';
                            }
                            description
                              "The name of a device.";
                        }
                    }
                }

                container yang-modules {
                    description
                      "The list yang modules supported by the device-adapter";
                    list module {
                        key "name revision";
                        description
                        "Each entry represents one revision of one module
                            currently supported by the server.";
                        leaf name {
                            type leafref {
                                path '/yanglib:modules-state/yanglib:module/yanglib:name';
                            }
                            config false;
                            description
                            "A reference to yang module name";
                        }
                        leaf revision {
                            type leafref {
                                path '/yanglib:modules-state/yanglib:module/yanglib:revision';
                            }
                            config false;
                            description
                            "A reference to yang module revision";
                        }
                    }
                }
                container factory-garment-tag {
                    when "../model != 'standard'";
                    description
                        "This container contains a list of items which was specific to the VDA";
                    leaf total-number-of-modules-present {
                        config false;
                        type string;
                        description
                            "Total number of modules present in corresponding standard adapter";
                    }
                    leaf number-of-modules-present-in-standard-adapter {
                        config false;
                        type string;
                        description
                            "Total number of modules present in corresponding standard adapter";
                    }
                    leaf percentage-adherence-to-standard-module {
                        config false;
                        type string;
                        description
                            "VDA's adherence percentage to standard modules";
                    }
                    leaf-list deviated-standard-module {
                        config false;
                        type string;
                        description
                            "list of standard modules that are having deviations";
                    }
                    leaf percentage-of-standard-modules-having-deviation {
                        config false;
                        type string;
                        description
                            "percentage of standard modules that are having deviations added in vda";
                    }
                    leaf-list augmented-standard-module {
                        config false;
                        type string;
                        description
                            "list of standard modules that are having augmentations";
                    }
                    leaf percentage-of-standard-modules-having-augments {
                        config false;
                        type string;
                        description
                            "percentage of standard modules that are having deviations added in vda";
                    }
                }
            }
        }
    }
}
