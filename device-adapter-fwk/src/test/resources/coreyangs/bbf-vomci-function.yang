module bbf-vomci-function {
  yang-version 1.1;
  namespace "urn:bbf:yang:bbf-vomci-function";
  prefix bbf-vomci-func;

  import bbf-yang-types {
    prefix bbf-yang;
  }
  
  import bbf-vomci-types {
    prefix bbf-vomcit;
  }

  import bbf-network-function-client {
    prefix bbf-nfc;
  }
  
  import bbf-omci-message-retransmission {
    prefix bbf-omci-mr;
  }
  
  import bbf-vomci-entity {
    prefix bbf-vomci-ent;
  }
  
  import bbf-voltmf-message-monitor {
    prefix bbf-voltmf-msg-mon;
  }

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     WA Director: George Dobrowski, Morris Creek Consulting

     WA Director: Bruno Cornaglia, Vodafone";
  description
    "This module contains a collection of YANG definitions needed
     for vOMCI function as described in TR-451.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2021-08-19 {
    description
      "Initial revision.";
    reference
      "TR-451: Section 5.2 vOMCI Function Description
               Section 5.7 vOLTMF to vOMCI function Interface
               Section 5.8 vOMCI function to OLT Interface";
  }

  // Features
  feature nf-client-supported {
    description
      "Indicates that client connectivity to network function's
       endpoints are supported.";
  }

  feature nf-server-supported {
    description
      "Indicates that server connectivity for network function's 
       endpoints are supported.";
  }

  // Notifications
  notification onu-alignment-result {
    description
      "The notification that the vOMCI function has completed an
       alignment on an ONU.";
    leaf onu-name {
      type bbf-vomcit:onu-name;
      description
        "The name of the ONU that is the target of the alignment 
         result.";
    }
    leaf datastore-tag {
      type string;
      description
        "The datastore tag associated with the ONU's configuration
         data kept by the vOMCI function.";
    }
    leaf alignment-status {
      type bbf-vomcit:onu-alignment-status;
      description
        "The alignment status of the ONU.";
    }
  }
  
  notification onu-alarm-misalignment {
    description
      "The vOMCI function dectected a gap in the OMCI alarm 
        message's sequence number.";
    leaf onu-name {
      type bbf-vomcit:onu-name;
      description
        "The name of the ONU that is the target of the alignment 
         result.";
    }
    leaf detected-sequence-number {
      type bbf-vomcit:omci-sequence-number; 
      description
        "The sequence number that resulted in the misalignment.";
    }
  }

  notification untranslated-omci-notification {
    description
      "The vOMC Message function cannot translate an 
       OMCI Alarm or AVC message into a specific YANG 
       notification.";
    leaf onu-name {
      type bbf-vomcit:onu-name;
      description
        "The name of the ONU.";
    }
    anydata untranslated-data {
      description
        "The data received by the vOMCI function that could not be 
         translated.";
    }
  }
  
  notification unsupported-version-vomci-function-message {
    description
      "The vOMCI function does not support the version of the message 
       sent by the vOLTMF.";
    leaf request-payload-id {
      type string;
      description
        "The request payload identifier.";
    }
    leaf message-version {
      type string;
      description
        "The version that was on the message.";
    }
    leaf-list supported-message-versions {
      type string;
      description
        "The version(s) that are supported by the vOMCI function.";
    }
  }

  container managed-onus {
    description
      "The ONUs that are being managed by this entity.";
    action create-onu {
      description
        "Provides the ability to create an ONU within the vOMCI 
         function.";
      input {
        leaf name {
          type bbf-vomcit:onu-name;
          description
            "The unique name of the ONU.";
        }
      }
    }
    list managed-onu {
      key "name";
      config false;
      description
        "The list of ONUs that are being managed by this entity.";
      leaf name {
        type bbf-vomcit:onu-name;
        description
          "The unique name of the ONU.";
      }
      action delete-onu {
        description
          "Provides the ability to delete an ONU within the vOMCI 
           function.";
      }
      action set-onu-communication {
        description
          "Provides the ability to configure the information necessary
           to establish if an ONU can be communicated with by the
           vOMCI function along with remote endpoint to use.";
        input {
          leaf onu-communication-available {
            type boolean;
            description
              "When true, the ONU is able to be communicated with 
               across the ONU management chain of entities.";
          }
          leaf olt-remote-endpoint-name {
            type bbf-yang:string-ascii64;
            description
              "The remote endpoint name to use for transmitting vOMCI 
               messages toward the OLT.";
          }
          leaf voltmf-remote-endpoint-name {
            type bbf-yang:string-ascii64;
            description
              "The remote endpoint name to use for transmitting YANG 
               messages toward the vOLTMF.";
          }
          uses bbf-vomci-ent:vomci-onu-header;
        }
      }
      uses bbf-vomci-ent:vomci-onu-header;
      leaf onu-communication-available {
        type boolean;
        description
          "When true, the ONU is able to be communicated with across 
           the ONU management chain of entities.";
      }
      leaf olt-remote-endpoint-name {
        type bbf-yang:string-ascii64;
        description
          "The name remote endpoint to use for transmitting vOMCI 
           messages toward the OLT.";
      }
      
      container statistics {
        description
          "vOMCI message and retransmission statistics.";
        action reset {
          description
            "Provides the capability to reset the counters of the 
             statistics.";
        }
        uses bbf-vomci-ent:vomci-message-statistics;
        uses bbf-omci-mr:omci-msg-retrans-statistics;
      }
    }
  }

  container vomci {
    description
      "The configuration data associated with the vOMCI function.";
    leaf vomci-msg-timeout {
      type uint16 {
        range "10..max";
      }
      units "seconds";
      default "900";
      description
        "The maximum number of seconds that a vOMCI message is 
         transmitted and has not been responded. The timeout used to 
         cleanup stale vOMCI messages. The timeout is only applicable 
         when OMCI message retransmission capability is not currently 
         enabled for this entity.";
    }
  
    container omci-message-retransmission {
      if-feature "bbf-omci-mr:omci-msg-retrans-supported";
      description
        "OMCI message retransmission capability.";
      uses bbf-omci-mr:omci-msg-retrans-grouping;
    } //OMCI message retransmission capability

  
    container remote-network-function {
      presence "Enables access to remote network functions";
      description
        "Remote network function (NF) configuration.";
      container nf-client {
        if-feature "bbf-vomci-func:nf-client-supported";
        description
          "Client network function configuration.";
        leaf enabled {
          type boolean;
          default "true";
          description
            "Administratively enable the use of the client 
             connectivity capability to the network function.";
        }
        uses bbf-nfc:nf-endpoint-grouping;
      } //nf-client
  
      container nf-server {
        if-feature "bbf-vomci-func:nf-server-supported";
        description
          "Server network function configuration.";
        leaf enabled {
          type boolean;
          default "true";
          description
            "Administratively enable the use of the server 
             connectivity capability for connecting network 
             function.";
        }
      } //nf-server
    }
    container statistics {
      config false;
      description
        "The OMCI function statistics.";
      action reset {
        description
          "Provides the capability to reset the counters of the 
           statistics.";
      }
      uses bbf-omci-mr:omci-msg-retrans-statistics;
      container voltmf-statistics {
        config false;
        description
          "Counters for the vOLTMF messages sent between the vOLTMF 
           and the vOMCI function.";
        uses bbf-voltmf-msg-mon:voltmf-msg-statistics-grouping;
      }
    }
  }
}
