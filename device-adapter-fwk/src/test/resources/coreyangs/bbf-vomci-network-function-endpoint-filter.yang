module bbf-vomci-network-function-endpoint-filter {
  yang-version 1.1;
  namespace "urn:bbf:yang:bbf-vomci-network-function-endpoint-filter";
  prefix bbf-vomci-nf-epf;

  import bbf-vomci-types {
    prefix bbf-vomci-types;
  }

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     WA Director: George Dobrowski, Morris Creek Consulting

     WA Director: Bruno Cornaglia, Vodafone";
  description
    "This module contains a collection of YANG definitions needed to
     communicate with endpoints of vOMCI network functions as 
     described in TR-451.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2021-08-19 {
    description
      "Initial revision.";
    reference
      "TR-451: Section 5.5.1 vOMCI Function Connectivity";
  }

  // Typedefs
  typedef onu-endpoint-criteria-type {
    type enumeration {
      enum any-onu {
        description
          "The ONU criteria is valid for any ONU.";
      }
      enum onu-vendor {
        description
          "The ONU criteria is identified by the vendor's 
           identifier.";
      }
    }
    description
      "The types for criteria related to ONU endpoint filters.";
  }
  
  typedef onu-vomci-criteria-type {
    type enumeration {
      enum any-onu {
        description
          "The ONU criteria is valid for any ONU.";
      }
      enum onu-vendor {
        description
          "The ONU criteria is identified by the vendor's 
           identifier.";
      }
      enum onu-software-version {
        description
          "The ONU criteria is identified by the software version of 
           the ONU.";
      }
    }
    description
      "The types for criteria related to ONU vOMCI filters.";
  }

  // Groupings
  grouping onu-endpoint-criteria-grouping {
    description
      "The choice allows to specify combinations of ONU criteria 
       values or to indicate any ONU.";
    leaf rule-type {
      type onu-endpoint-criteria-type;
      default "any-onu";
      description
        "The type of ONU endpoint filter criteria to apply to this 
         rule.";
    }
    leaf onu-vendor {
      when "../rule-type = 'onu-vendor'" {
        description
          "Only valid when the type is the ONU vendor.";
      }
      type bbf-vomci-types:onu-vendor-id;
      description
        "ONU vendor as defined in the TC layer ONU-ID.";
    }
  }

  grouping onu-vomci-criteria-grouping {
    description
      "The choice allows to specify combinations of ONU criteria
       values to indicate any ONU for vOMCI selection.";
    leaf rule-type {
      type onu-vomci-criteria-type;
      default "any-onu";
      description
        "The type of ONU vOMCI selection criteria to apply to this 
         rule.";
    }
    leaf onu-vendor {
      when "../rule-type = 'onu-vendor'" {
        description
          "Only valid when the type is the ONU vendor.";
      }
      type bbf-vomci-types:onu-vendor-id;
      description
        "ONU vendor as defined in the TC layer ONU-ID.";
    }
    leaf onu-vendor-software-version {
      when "../rule-type = 'onu-software-version'" {
        description
          "Only valid when the type is the ONU's software version.";
      }
      type bbf-vomci-types:onu-vendor-software-version;
      description
        "ONU vendor's software version.";
    }
  }
}
