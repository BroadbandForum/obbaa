module ietf-ipv4-unicast-routing {

  namespace "urn:ietf:params:xml:ns:yang:ietf-ipv4-unicast-routing";

  prefix "v4ur";

  import ietf-routing {
    prefix "rt";
  }

  import ietf-inet-types {
    prefix "inet";
  }

// WORKAROUND: NOT SUPPORTED BY ANV - COPYING DEFINITION of next-hop-content from ietf-routing.yang here - See also FNMS-6874
  import ietf-interfaces {
    prefix "if";
  }

  organization
    "IETF NETMOD (NETCONF Data Modeling Language) Working Group";

  contact
    "WG Web:   <http://tools.ietf.org/wg/netmod/>
     WG List:  <mailto:netmod@ietf.org>

     WG Chair: Thomas Nadeau
               <mailto:tnadeau@lucidvision.com>

     WG Chair: Juergen Schoenwaelder
               <mailto:j.schoenwaelder@jacobs-university.de>

     WG Chair: Kent Watsen
               <mailto:kwatsen@juniper.net>

     Editor:   Ladislav Lhotka
               <mailto:lhotka@nic.cz>";

  description
    "This YANG module augments the 'ietf-routing' module with basic
     configuration and state data for IPv4 unicast routing.

     Copyright (c) 2015 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     The key words 'MUST', 'MUST NOT', 'REQUIRED', 'SHALL', 'SHALL
     NOT', 'SHOULD', 'SHOULD NOT', 'RECOMMENDED', 'MAY', and
     'OPTIONAL' in the module text are to be interpreted as described
     in RFC 2119 (http://tools.ietf.org/html/rfc2119).

     This version of this YANG module is part of RFC XXXX
     (http://tools.ietf.org/html/rfcXXXX); see the RFC itself for
     full legal notices.";

  revision 2015-10-16 {
    description
      "Initial revision.";
    reference
      "RFC XXXX: A YANG Data Model for Routing Management";
  }

  /* Identities */

  identity ipv4-unicast {
    base rt:ipv4;
    description
      "This identity represents the IPv4 unicast address family.";
  }

  /* State data */

  augment "/rt:routing-state/rt:routing-instance/rt:ribs/rt:rib/"
        + "rt:routes/rt:route" {
    when "../../rt:address-family = 'v4ur:ipv4-unicast'" {
      description
        "This augment is valid only for IPv4 unicast.";
    }
    description
      "This leaf augments an IPv4 unicast route.";
    leaf destination-prefix {
      type inet:ipv4-prefix;
      description
        "IPv4 destination prefix.";
    }
  }

  augment "/rt:routing-state/rt:routing-instance/rt:ribs/rt:rib/"
        + "rt:routes/rt:route/rt:next-hop/rt:next-hop-options/rt:simple-next-hop" {
    when "../../../rt:address-family = 'v4ur:ipv4-unicast'" {
      description
        "This augment is valid only for IPv4 unicast.";
    }
    description
      "Augment 'next-hop-options' in IPv4 unicast routes.";
    leaf next-hop-address {
      type inet:ipv4-address;
      description
        "IPv4 address of the next-hop.";
    }
  }

  /* Configuration data */

  augment "/rt:routing/rt:routing-instance/rt:routing-protocols/"
        + "rt:routing-protocol/rt:static-routes" {
    description
      "This augment defines the configuration of the 'static'
       pseudo-protocol with data specific to IPv4 unicast.";
    container ipv4 {
      description
        "Configuration of a 'static' pseudo-protocol instance
         consists of a list of routes.";
      list route {
        key "destination-prefix";
        description
          "A list of static routes.";
        leaf destination-prefix {
          type inet:ipv4-prefix;
          mandatory "true";
          description
            "IPv4 destination prefix.";
        }
        leaf description {
          type string;
          description
            "Textual description of the route.";
        }
        container next-hop {
          description
            "Configuration of next-hop.";
// WORKAROUND: NOT SUPPORTED BY ANV - COPYING DEFINITION of next-hop-content from ietf-routing.yang here - See also FNMS-6874
    choice next-hop-options {
      mandatory "true";
      description
        "Options for next-hops in static routes.

         Modules for address families MUST augment this choice with
         the 'next-hop-address' case, which is a leaf containing a
         gateway address of that address family.

         It is expected that further cases will be added through
         augments from other modules, e.g., for Equal-Cost Multipath
         routing (ECMP).";
      case simple-next-hop {
        description
          "This case represents a simple next hop consisting of the
           next-hop address and/or outgoing interface.

           Modules for address families MUST augment this case with a
           leaf containing a next-hop address of that address
           family.";
          leaf outgoing-interface {
            type if:interface-ref;
            description
              "Name of the outgoing interface.";
          }
      }
      case special-next-hop {
        uses rt:special-next-hop;
      }
      case next-hop-address {
              leaf next-hop-address {
                type inet:ipv4-address;
                description
                  "IPv4 address of the next-hop.";
              }
      }
    }
// WORKAROUND: NOT SUPPORTED BY ANV - See also FNMS-6874
/*
          uses rt:next-hop-content {
            augment "next-hop-options" {
              description
                "Augment 'next-hop-options' in IPv4 static routes.";
              leaf next-hop-address {
                type inet:ipv4-address;
                description
                  "IPv4 address of the next-hop.";
              }
            }
          }
*/
        }
      }
    }
  }

  /* RPC operations */

  augment "/rt:fib-route/rt:input/rt:destination-address" {
    when "rt:address-family='v4ur:ipv4-unicast'" {
      description
        "This augment is valid only for IPv4 unicast.";
    }
    description
      "This leaf augments the 'rt:destination-address' parameter of
       the 'rt:fib-route' operation.";
    leaf address {
      type inet:ipv4-address;
      description
        "IPv4 destination address.";
    }
  }

  augment "/rt:fib-route/rt:output/rt:route" {
    when "rt:address-family='v4ur:ipv4-unicast'" {
      description
        "This augment is valid only for IPv4 unicast.";
    }
    description
      "This leaf augments the reply to the 'rt:fib-route'
       operation.";
    leaf destination-prefix {
      type inet:ipv4-prefix;
      description
        "IPv4 destination prefix.";
    }
  }

  augment "/rt:fib-route/rt:output/rt:route/rt:next-hop/"
        + "rt:next-hop-options/rt:simple-next-hop" {
    when "../rt:address-family='v4ur:ipv4-unicast'" {
      description
        "This augment is valid only for IPv4 unicast.";
    }
    description
      "Augment 'next-hop-options' in the reply to the 'rt:fib-route'
       operation.";
    leaf next-hop-address {
      type inet:ipv4-address;
      description
        "IPv4 address of the next-hop.";
    }
  }
}
