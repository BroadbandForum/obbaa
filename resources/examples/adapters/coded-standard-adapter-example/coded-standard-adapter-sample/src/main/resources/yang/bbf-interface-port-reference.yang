module bbf-interface-port-reference {
//  all yang v1.1 features have been commented out 
//  yang-version 1.1;

  namespace "urn:bbf:yang:bbf-interface-port-reference";

  prefix bbf-if-port-ref;
  
  import iana-if-type {
    prefix ianaift;
  }
  
  import ietf-interfaces {
    prefix if;
  }
  
  import ietf-hardware {
    prefix hw;
  }
  
  import iana-hardware {
    prefix ianahw;
  }
  
  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "A YANG Data model to augment the IETF interface model with a 
     reference to a port component.

     Copyright (c) 2017, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2017-03-13 {
    description
      "Initial revision.
       * Approval Date:    see revision date above.
       * Publication Date: yyyy-mm-dd.";
    reference
      "TR-383: Common YANG Modules
               <https://www.broadband-forum.org/technical/download/
                        TR-383.pdf>";
  }

  typedef hardware-ref {
    type leafref {
      path '/hw:hardware/hw:component/hw:name';
    }
    description
      "Used to reference to a port component.";
  }

  augment '/if:interfaces/if:interface' {
 //   when
 //     "derived-from-or-self (if:type, 'ianaift:fastdsl') or 
 //      derived-from-or-self (if:type, 'ianaift:ethernetCsmacd')";

    description
      "Only applicable for interface layers e.g. fastdsl, which need a
       reference to a port component.";

    leaf port-layer-if {
      if-feature "hw:hardware-config";
      type hardware-ref;
 //     must
 //       "derived-from-or-self (/hw:hardware
 //        /hw:component[hw:name=current()]/hw:class,
 //        'ianahw:port')" {
 //       error-message
 //         "Referenced component is or is derived from class 'port'.";
 //     }
 //     min-elements 1;
      description
        "A list of references to the physical port components 
         corresponding to this interface.";
    }
  }

  augment '/if:interfaces-state/if:interface' {
  //  when
  //   "derived-from-or-self (if:type, 'ianaift:fastdsl') or 
  //    derived-from-or-self (if:type, 'ianaift:ethernetCsmacd')";

    description
      "Only applicable for interface layers e.g. fastdsl, which need a
       reference to a port component.";

    leaf port-layer-if {
      if-feature "hw:hardware-config";
      type hardware-ref;
 //     must
 //       "derived-from-or-self (/hw:hardware
 //        /hw:component[hw:name=current()]/hw:class,
 //        'ianahw:port')" {
 //       error-message
 //         "Referenced component is or is derived from class 'port'.";
 //     }
      description
        "A list of references to the physical port component used to 
         support this interface.";
    }
  }
}
