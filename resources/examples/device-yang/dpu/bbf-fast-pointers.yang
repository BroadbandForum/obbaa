submodule bbf-fast-pointers {
//  yang-version 1.1;
  belongs-to bbf-fast {
    prefix bbf-fast;
  }

  import ietf-interfaces {
    prefix if;
  }

  import bbf-fastdsl {
    prefix bbf-fastdsl;
  }

  import bbf-yang-types {
    prefix bbf-yang;
  }

  include bbf-fast-base;

  /* Profile Definitions */
  include bbf-fast-service-profiles;
  include bbf-fast-spectrum-profiles;
  include bbf-fast-quality-profiles;
  include bbf-fast-tdd-profiles;
  include bbf-fast-threshold-management;
  include bbf-fast-perf-types;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for
     managing Vector of Profiles (VoP) on FAST interfaces.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef line-config-vector-ref {
    type leafref {
      path '/bbf-fast:fast/bbf-fast:vectors/bbf-fast:line-config-'
         + 'vector/bbf-fast:name';
    }
    description
      "Used to reference a line configuration vector of profiles";
  }

  typedef threshold-template-ref {
    type leafref {
      path '/bbf-fast:fast/bbf-fast:thresholds/bbf-fast:threshold-'
         + 'template/bbf-fast:name';
    }
    description
      "Used to reference a line threshold template profile";
  }

  grouping profile-vector {
    description
      "A vector of profiles used to configure the line";

    leaf time-division-duplexing-profile {
      type time-division-duplexing-profile-ref;
      mandatory true;
      description
        "References a time division duplexing(TDD) profile to be
         used to configure the line.";
    }

    leaf downstream-data-rate-profile {
      type downstream-data-rate-profile-ref;
      mandatory true;
      description
        "References a downstream data rate profile to be used to
         configure the line.";
    }

    leaf upstream-data-rate-profile {
      type upstream-data-rate-profile-ref;
      mandatory true;
      description
        "References an upstream data rate profile to be used to
         configure the line.";
    }

    leaf low-power-data-rate-profile {
      type low-power-data-rate-profile-ref;
      mandatory true;
      description
        "References a low power data rate profile to be used to
         configure the line.";
    }

    leaf line-spectrum-profile {
      type line-spectrum-profile-ref;
      mandatory true;
      description
        "References a line spectrum profile to be used to configure
         the line.";
    }

    leaf upstream-power-back-off-profile {
      type upstream-power-back-off-profile-ref;
      mandatory true;
      description
        "References an upstream power-back-off profile to be used to
         configure the line.";
    }

    leaf radio-frequency-interference-profile {
      type radio-frequency-interference-profile-ref;
      mandatory true;
      description
        "References a RFI profile to be used to configure the
         line.";
    }

    leaf noise-margin-profile {
      type noise-margin-profile-ref;
      mandatory true;
      description
        "References a noise margin profile to be used to configure
         the line.";
    }

    leaf fast-rate-adaptation-profile {
      type fast-rate-adaptation-profile-ref;
      mandatory true;
      description
        "References a fast rate adaptation profile to be used to
         configure the line.";
    }

    leaf retransmission-profile {
      type retransmission-profile-ref;
      mandatory true;
      description
        "References a retransmission profile to be used to configure
         the line.";
    }

    leaf fast-retrain-policy-profile {
      type fast-retrain-policy-profile-ref;
      mandatory true;
      description
        "References a fast retrain policy profile to be used to
         configure the line.";
    }

    leaf vectoring-profile {
      type vectoring-profile-ref;
      mandatory true;
      description
        "References a vectoring profile to be used to configure the
         line.";
    }
  }

  augment '/bbf-fast:fast/bbf-fast:vectors' {
    description
      "Data nodes to support line configuration vectors.";

    list line-config-vector {
      key "name";
      description
        "A list of line configuration vectors aka vector of profiles
         (VoP).";

      leaf name {
        type bbf-yang:string-ascii64;
        description
          "Uniquely identifies the line configuration vector.";
      }

      uses profile-vector;
    }
  }

  augment '/bbf-fast:fast/bbf-fast:thresholds' {
    description
      "Data nodes to support performance threshold profiles and
       templates.";

    list threshold-template {
      key "name";
      description
        "A template defining the threshold profiles to apply to
         performance parameters of a FAST interface.";

      leaf name {
        type bbf-yang:string-ascii64;
        description
          "Uniquely identifies the line configuration vector.";
      }

      leaf ftu-o-15min-line-threshold-profile {
        type line-threshold-profile-ref;
        mandatory true;
        description
          "Reference to a line threshold profile for FTU-O
           thresholds related to 15 minute performance
           counters";
      }

      leaf ftu-o-24hr-line-threshold-profile {
        if-feature "performance-24hr";
        type line-threshold-profile-ref;
        mandatory true;
        description
          "Reference to a line threshold profile for FTU-O
           thresholds related to 24 hour performance
           counters";
      }

      leaf ftu-r-15min-line-threshold-profile {
        type line-threshold-profile-ref;
        mandatory true;
        description
          "Reference to a line threshold profile for FTU-R
           thresholds related to 15 minute performance
           counters";
      }

      leaf ftu-r-24hr-line-threshold-profile {
        if-feature "performance-24hr";
        type line-threshold-profile-ref;
        mandatory true;
        description
          "Reference to a line threshold profile for FTU-R
           thresholds related to 24 hour performance
           counters";
      }

      leaf ftu-o-15min-channel-threshold-profile {
        type channel-threshold-profile-ref;
        mandatory true;
        description
          "Reference to a channel threshold profile for FTU-O
           thresholds related to 15 minute performance
           counters";
      }

      leaf ftu-o-24hr-channel-threshold-profile {
        if-feature "performance-24hr";
        type channel-threshold-profile-ref;
        mandatory true;
        description
          "Reference to a channel threshold profile for FTU-O
           thresholds related to 24 hour performance
           counters";
      }

      leaf ftu-r-15min-channel-threshold-profile {
        type channel-threshold-profile-ref;
        mandatory true;
        description
          "Reference to a channel threshold profile for FTU-R
           thresholds related to 15 minute performance
           counters";
      }

      leaf ftu-r-24hr-channel-threshold-profile {
        if-feature "performance-24hr";
        type channel-threshold-profile-ref;
        mandatory true;
        description
          "Reference to a channel threshold profile for FTU-R
           thresholds related to 24 hour performance
           counters";
      }
    }
  }


  augment '/if:interfaces/if:interface/bbf-fastdsl:line/bbf-fast:'
        + 'line' {
    description
      "Data nodes to support the assignment of a profile vector.";

    choice profile-config {
      default "no-profiles-attached";
      description
        "Provides methods for direct or indirect attachment of
         the profile vector";

      case no-profiles-attached {
        leaf no-profiles-attached {
          type empty;
          description
            "If present, indicates that no profiles are attached
             to this line";
        }
      }

      case direct-attachment-mode {
        uses profile-vector;
      }

      case indirect-attachment-mode {
        leaf line-config-vector {
          type line-config-vector-ref;
          mandatory true;
          description
            "Assigns a Line Configuration Vector to a FAST line.";
        }
      }
    }

    leaf threshold-template {
      type threshold-template-ref;
      description
        "Assigns a threshold template to a FAST line.";
    }
  }
}
