module tailf-aaa {
  namespace "http://tail-f.com/ns/aaa/1.1";
  prefix aaa;
  tailf:id "http://tail-f.com/ns/aaa";

  import ietf-netconf-acm {
    prefix nacm;
  }

  import iana-crypt-hash {
    prefix ianach;
  }

  import tailf-common {
    prefix tailf;
  }

  organization "Tail-f Systems";

  description
    "This module defines the Tail-f AAA data model.";

  revision 2015-06-16 {
    description
      "Released as part of ConfD-6.0 / NSO-4.0.

       Added /aaa/authentication/users/user/change-password action.";
  }

  revision 2014-08-29 {
    description
      "Released as part of ConfD-5.2.1 / NCS-3.2.1.

       Removed max-elements restriction on /aaa/authentication/users/user.";
  }

  revision 2014-06-30 {
    description
      "Released as part of ConfD-5.2 / NCS-3.2.

       Changed passwdStr typedef to use ianach:crypt-hash instead of
       tailf:md5-digest-string.";
  }

  revision 2013-03-07 {
    description
      "Released as part of ConfD-4.2.

       Added nacm:default-deny-all extension for /aaa and /user, and
       nacm:default-deny-write extension for /alias and /session.";
  }

  revision 2012-11-08 {
    description
      "Released as part of ConfD-4.1.

       Removed /aaa/authentication/groups and /aaa/authorization,
       since this functionality is modeled in
       ietf-netconf-acm.yang as augmented by tailf-acm.yang.";
  }

  revision 2011-09-22 {
    description
      "Released as part of ConfD-3.7.";
  }

  revision 2010-06-17 {
    description
      "Released as part of ConfD-3.3.";
  }

  revision 2010-04-22 {
    description
      "Released as part of ConfD-3.2.1.";
  }

  revision 2010-03-18 {
    description
      "Released as part of ConfD-3.2.";
  }

  typedef history {
    type uint64 {
      range "0 .. 8192";
    }
  }
  typedef idle-timeout {
    type uint64 {
      range "0 .. 8192";
    }
  }
  typedef display-level {
    type uint64 {
      range "1 .. 64";
    }
  }
  typedef passwdStr {
    type ianach:crypt-hash;
  }
  typedef levelInt {
    type int32 {
      range "0 .. 15";
    }
  }
  typedef modeStr {
    type union {
      type string;
      type builtinModes;
    }
  }
  typedef builtinModes {
    type enumeration {
      enum exec;
      enum configure;
    }
  }

  grouping session-params {
    leaf complete-on-space {
      type boolean;
      tailf:info "Enable/disable completion on space";
    }
    leaf ignore-leading-space {
      type boolean;
      tailf:info "Ignore leading whitespace";
    }
    leaf idle-timeout {
      type idle-timeout;
      tailf:info "CLI idle-timeout in seconds";
    }
    leaf paginate {
      type boolean;
      tailf:info "Paginate output from CLI commands";
    }
    leaf history {
      type history;
      tailf:info "History size";
    }
    leaf autowizard {
      type boolean;
      tailf:info "Automatically query user for mandatory elems";
    }
    leaf show-defaults {
      type boolean;
      tailf:info "Show default values when showing the configuration";
    }
    leaf display-level {
      type display-level;
      tailf:info "Max depth to show when displaying configuration";
    }
    leaf prompt1 {
      type string;
      tailf:info "Prompt for operational mode";
    }
    leaf prompt2 {
      type string;
      tailf:info "Prompt for configure mode";
    }
  }

  container aaa {
    tailf:info "AAA management";
    nacm:default-deny-all;
    container authentication {
      tailf:info "User management";
      container users {
        tailf:info "List of local users";
        list user {
          key name;
          leaf name {
            type string;
            tailf:info "Login name of the user";
          }
          leaf uid {
            type int32;
            mandatory true;
            tailf:info "User Identifier";
          }
          leaf gid {
            type int32;
            mandatory true;
            tailf:info "Group Identifier";
          }
          leaf password {
            type passwdStr;
            mandatory true;
          }
          leaf ssh_keydir {
            type string;
            mandatory true;
            tailf:info "Absolute path to directory where user's ssh keys
                        may be found";
          }
          leaf homedir {
            type string;
            mandatory true;
            tailf:info "Absolute path to user's home directory";
          }
          tailf:action change-password {
            tailf:info "Request password change";
            tailf:actionpoint internal {
              tailf:internal;
            }
            input {
              leaf old-password {
                type string;
                mandatory true;
                tailf:info "Old password";
                tailf:suppress-echo true;
              }
              leaf new-password {
                type string;
                mandatory true;
                tailf:info "New password";
                tailf:suppress-echo true;
              }
              leaf confirm-password {
                type string;
                mandatory true;
                tailf:info "Confirm New password";
                tailf:suppress-echo true;
              }
            }
          }
        }
      }
    }
    container ios {
      tailf:info "Specific IOS settings";
      presence "";

      list level {
        key nr;
        min-elements 2;
        leaf nr {
          type levelInt;
        }
        leaf secret {
          type passwdStr;
        }
        leaf password {
          type passwdStr;
        }
        leaf prompt {
          type string;
          default "h# ";
        }
      }

      list privilege {
        key mode;
        leaf mode {
          type modeStr;
        }
        list level {
          key nr;
          min-elements 1;
          max-elements 15;
          leaf nr {
            type levelInt;
          }
          list command {
            key name;
            leaf name {
              type string;
            }
          }
        }
      }
    }
  }
  list alias {
    nacm:default-deny-write;
    key name;
    tailf:info "Create command alias.";
    leaf name {
      type string;
      tailf:info "Name of the command alias. An alias name can be a single
                  word or multiple words joined by a dash (-).";
    }
    leaf expansion {
      type string;
      mandatory true;
      tailf:info "Original command syntax. Valid abbreviations of the original
                  command syntax can be entered for the command-syntax
                  argument.";
    }
  }
  container session {
    nacm:default-deny-write;
    uses session-params;
    presence "";
    tailf:info "Global default CLI session parameters";
  }
  list user {
    tailf:info "User specific command aliases and default CLI session
                parameters";
    nacm:default-deny-all;
    key name;
    leaf name {
      type string;
    }
    leaf description {
      type string;
      tailf:info "User description";
    }
    list alias {
      key name;
      tailf:info "Create command alias.";
      leaf name {
        type string;
        tailf:info "Name of the command alias. An alias name can be a single
                    word or multiple words joined by a dash (-).";
      }
      leaf expansion {
        type string;
        mandatory true;
        tailf:info "Original command syntax. Valid abbreviations of the original
                    command syntax can be entered for the command-syntax
                    argument.";
      }
    }
    container session {
      uses session-params;
      tailf:info "User specific default CLI session parameters";
    }
  }

}
