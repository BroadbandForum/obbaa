module bbf-subscriber-types {
  //yang-version 1.1;
  namespace "urn:bbf:yang:bbf-subscriber-types";

  prefix bbf-subtype;

  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "A YANG Data Model for defining common types associated with
     subscribers and subscriber protocols.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2016-07-06 {
    description
      "Initial revision.
       * Approval Date:    see revision date above.
       * Publication Date: yyyy-mm-dd.";

    reference
      "TR-383: Common YANG Modules
               <https://www.broadband-forum.org/technical/download/
                        TR-383.pdf>";
  }

  /****************************************************
   * New Typedefs added within this contribution
   ****************************************************/

  typedef string-ascii63-or-empty {
    type string {
      length "0..63";
      pattern '[ -~]*'; // allows the 95 printable ASCII characters
    }
    description
      "Used where a string is needed which has a maximum length of 
       63 characters and also allows for a null string (length = 0).
       The character set is limited to the 95 printable ascii 
       characters as defined in https://en.wikipedia.org/wiki/ASCII.";
  }

  typedef broadband-line-characteristics {
    type bits {
      bit actual-data-rate-upstream {
        description
          "Sub-option type 0x81 - Actual upstream data rate 
           of an access loop.";

        reference
          "ITU-T G.997 Section 7.5.2.1.";
      }
      bit actual-data-rate-downstream {
        description
          "Sub-option type 0x82 - Actual downstream data rate 
           of an access loop.";

        reference
          "ITU-T G.997 Section 7.5.2.1.";
      }
      bit min-data-rate-upstream {
        description
          "Sub-option type 0x83 - Minimum upstream data rate 
           at which the loop is set to operate.";

        reference
          "ITU-T G.997 Section 7.3.1.1.1.";
      }
      bit min-data-rate-downstream {
        description
          "Sub-option type 0x84 - Minimum downstream data 
           rate at which the loop is set to operate.";

        reference
          "ITU-T G.997 Section 7.3.1.1.1.";
      }
      bit attainable-data-rate-upstream {
        description
          "Sub-option type 0x85 - Maximum upstream data 
           rate that can be achieved.";

        reference
          "ITU-T G.997 Section 7.5.1.12 and 7.5.1.13.";
      }
      bit attainable-data-rate-downstream {
        description
          "Sub-option type 0x86 - Maximum downstream data 
           rate that can be achieved.";

        reference
          "ITU-T G.997 Section 7.5.1.12 and 7.5.1.13.";
      }
      bit max-data-rate-upstream {
        description
          "Sub-option type 0x87 - Maximum upstream data rate 
           at which the loop is set to operate.";

        reference
          "ITU-T G.997 Section 7.3.2.1.3.";
      }
      bit max-data-rate-downstream {
        description
          "Sub-option type 0x88 - Maximum downstream data 
           rate at which the loop is set to operate.";

        reference
          "ITU-T G.997 Section 7.3.2.1.3.";
      }
      bit min-data-rate-upstream-low-power-state {
        description
          "Sub-option type 0x89 - Minimum upstream data rate 
           at which the loop is set to operate during the low
           power state (L1/L2).";

        reference
          "ITU-T G.997 Section 7.3.2.1.5.";
      }
      bit min-data-rate-downstream-low-power-state {
        description
          "Sub-option type 0x8A - Minimum downstream data 
           rate at which the loop is set to operate during 
           the low power state (L1/L2).";

        reference
          "ITU-T G.997 Section 7.3.2.1.5.";
      }
      bit max-interleaving-delay-upstream {
        description
          "Sub-option type 0x8B - Maximum one-way 
           interleaving delay in upstream.";

        reference
          "ITU-T G.997 Section 7.3.2.2.";
      }
      bit actual-interleaving-delay-upstream {
        description
          "Sub-option type 0x8C - Actual one-way 
           interleaving delay value in milliseconds
           corresponding to the interleaver setting
           in upstream.";

        reference
          "ITU-T G.997 Section 7.5.2.3.";
      }
      bit max-interleaving-delay-downstream {
        description
          "Sub-option type 0x8D - Maximum one-way 
           interleaving delay in downstream.";

        reference
          "ITU-T G.997 Section 7.3.2.2.";
      }
      bit actual-interleaving-delay-downstream {
        description
          "Sub-option type 0x8E - Actual one-way 
           interleaving delay value in milliseconds
           corresponding to the interleaver setting
           in downstream.";

        reference
          "ITU-T G.997 Section 7.5.2.3.";
      }
      bit access-loop-encapsulation {
        description
          "Sub-option type 0x90 - the data link protocol and
           the encapsulation overhead on the access loop.";

        reference
          "TR-101i2 - R164.";
      }
    }

    description
      "The type defined for the broadband line characteristics
       listed in TR-101i2.";

    reference
      "TR-178i1 - R124.";
  }
}
