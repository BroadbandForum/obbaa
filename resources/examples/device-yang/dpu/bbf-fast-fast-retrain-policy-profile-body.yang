submodule bbf-fast-fast-retrain-policy-profile-body {
//  yang-version 1.1;
  belongs-to bbf-fast {
    prefix bbf-fast;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for
     managing fast retrain policy profiles.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping fast-retrain-policy-parameters {
    description
      "reinitialization configuration parameters applicable to both
       upstream and downstream.";
    reference
      "ITU-T G.997.2 clause 7.1.8.";

    leaf los-defect-persistency {
      type uint8 {
        range "1..20" {
          description
            "Defines a range equivalent to 0.1 to 2 seconds.";
        }
      }
      units "0.1 second";
      default "2";
      description
        "Defines the los defect persistency for triggering a
         reinitialization (see clause 12.1.4.2) at the FTU receiver,
         as part of the fast retrain policy.";
      reference
        "ITU-T G.997.2 clause 7.1.8.1 (LOS_PERSISTENCYds) and clause
         7.1.8.2 (LOS_PERSISTENCYus); ITU-T G.9701 clause
         12.1.4.3.1.";
    }

    leaf lom-defect-persistency {
      type uint8 {
        range "2..20" {
          description
            "Defines a range equivalent to 2 to 20
             seconds.";
        }
      }
      units "1 second";
      default "2";
      description
        "Defines the lom defect persistency for triggering a
         reinitialization (see clause 12.1.4.2) at the FTU receiver,
         as part of the fast retrain policy.";
      reference
        "ITU-T G.997.2 clause 7.1.8.3 (LOM_PERSISTENCYds) and clause
         7.1.8.4 (LOM_PERSISTENCYus); ITU-T G.9701 clause
         12.1.4.3.2.";
    }

    leaf lor-defect-persistency {
      type uint8 {
        range "1..20" {
          description
            "Defines a range equivalent to 0.1 to 2 seconds.";
        }
      }
      units "0.1 second";
      default "2";
      description
        "Defines the lor defect persistency for triggering a
         reinitialization (see clause 12.1.4.2) at the FTU receiver,
         as part of the fast retrain policy.";
      reference
        "ITU-T G.997.2 clause 7.1.8.5 (LOR_PERSISTENCYds) and clause
         7.1.8.6 (LOR_PERSISTENCYus); ITU-T G.9701 clause
         12.1.4.3.3.";
    }

    leaf reinit-time-threshold {
      type uint8 {
        range "5..31" {
          description
            "Defines a range equivalent to 5 to 31
             seconds.";
        }
      }
      units "1 second";
      default "10";
      description
        "Defines the threshold for the SES and eoc timeout
         conditions for declaring a High_BER event (see clause
         12.1.4.3.4) at the FTU receiver, as part of the
         fast retrain policy.";
      reference
        "ITU-T G.997.2 clause 7.1.8.7 (REINIT_TIME_THRESHOLDds) and
         clause 7.1.8.8 (REINIT_TIME_THRESHOLDus); ITU-T G.9701
         clause 12.1.4.3.4.";
    }

    leaf low-etr-threshold {
      type uint8 {
        range "0 | 1..30" {
          description
            "Defines a range equivalent to 1 to 30 seconds.";
        }
      }
      units "1 second";
      default "20";
      description
        "Defines the threshold for the low ETR condition for
         declaring a High_BER event (see clause 12.1.4.3.4) at the
         FTU receiver, as part of the fast retrain policy.
         The special value, 0, indicates that no High_BER event is
         declared based on ETR being below the ETR_min.";
      reference
        "ITU-T G.997.2 clause 7.1.8.9 (LOW_ETR_THRESHOLDds) and
         clause 7.1.8.10 (LOW_ETR_THRESHOLDus); ITU-T G.9701 clause
         12.1.4.3.4.";
    }
  }

  grouping fast-retrain-policy-profile {
    description
      "Defines the contents of a Fast Retrain Policy Profile.";

    container downstream {
      description
        "Downstream fast retrain policy parameters";

      uses fast-retrain-policy-parameters;
    }

    container upstream {
      description
        "Downstream fast retrain policy parameters";

      uses fast-retrain-policy-parameters;
    }
  }
}
