module bbf-mgmd-dev {

//  yang-version 1.1;

  namespace "urn:broadband-forum-org:yang:" +
            "bbf-mgmd-dev";  
            
  prefix "igmp-config-dev";

  /* import */ 
  import ietf-interfaces {
    prefix if;
  }
  
  import bbf-sub-interfaces{
	prefix bbf-subif;
  }

  import bbf-sub-interface-tagging{
	prefix bbf-subif-tag;
  }
    
  import bbf-mgmd {
    prefix "igmp-config";
  }   
  
  organization 
    "TBD";
    
  contact 
    "TBD";
    
  description 
    "An experimental YANG module for IGMP Protocol.";
  
  revision 2016-03-16 {
    description 
      "Initial revision.";
    reference
      "TBD";
  }
  
/**********************************************/
/* definitions which should always be present */
/**********************************************/

/*  deviation "/igmp-config:multicast/igmp-config:mgmd/igmp-config:multicast-vpn/igmp-config:multicast-subscriber-interface/igmp-config:interface-name"{
    deviate add{
      must "/if:interfaces/if:interface[if:name = current()]/if:type = 'bbfift:vlan-sub-interface' and /if:interfaces/if:interface[if:name = current()]/bbf-l2-fwd:interface-usage/bbf-l2-fwd:interface-usage = 'user-port'
      and count(/igmp-config:multicast/igmp-config:mgmd/igmp-config:multicast-vpn/igmp-config:multicast-subscriber-interface[igmp-config:interface-name = current()]) <= 1"{
      error-message "must be unique user-side subinterface";
      }
    }
  }
  
  deviation "/igmp-config:multicast/igmp-config:mgmd/igmp-config:multicast-vpn/igmp-config:multicast-subscriber-interface/igmp-config:max-group-number"{
    deviate add{
      must "current() <= /cap:capabilities/cap:capability[cap:cap-name='MAX_ACTIVE_ROOTS_PER_LINE']/cap:cap-def/cap:running-count"{
      error-message "max-group-number must less than 100";
      }
    }
  } 
  
  deviation "/igmp-config:multicast/igmp-config:mgmd/igmp-config:multicast-vpn/igmp-config:multicast-network-interface/igmp-config:multicast-vlan"{
    deviate add{
      must "/if:interfaces/if:interface[if:name = current()]/if:type = 'bbfift:vlan-sub-interface' and /if:interfaces/if:interface[if:name = current()]/bbf-l2-fwd:interface-usage/bbf-l2-fwd:interface-usage = 'network-port'
      and count(/igmp-config:multicast/igmp-config:mgmd/igmp-config:multicast-vpn/igmp-config:multicast-network-interface[igmp-config:multicast-vlan = current()]) <= 1"{
      error-message "must be unique network-side subinterface";
      }
    }
  }*/    
 
    /*deviation "/igmp-config:multicast/igmp-config:mgmd/igmp-config:multicast-vpn/igmp-config:multicast-network-interface/igmp-config:multicast-vlan"{
// WORKAROUND FNMS-17404
//    deviate add{
//      must "count(/if:interfaces/if:interface[if:name = current()]/bbf-subif:frame-processing/bbf-subif:ingress-rule/bbf-subif:rule/bbf-subif:flexible-match/bbf-subif-tag:match-criteria/bbf-subif-tag:tag) = 1"{
//      error-message "must not be S+C";
//      }
//    }
//  }  
  
/*  deviation "/igmp-config:multicast/igmp-config:mgmd/igmp-config:multicast-vpn/igmp-config:multicast-network-interface/igmp-config:multicast-vlan"{
    deviate add{  
      must "count(/bbf-l2-fwd:forwarding/bbf-l2-fwd:forwarders/bbf-l2-fwd:forwarder[bbf-l2-fwd:ports/bbf-l2-fwd:port/sub-interface = current()])=1
      and
      count(/bbf-l2-fwd:forwarding/bbf-l2-fwd:flooding-policies-profiles/bbf-l2-fwd:flooding-policies-profile[bbf-l2-fwd:name = /bbf-l2-fwd:forwarding/bbf-l2-fwd:forwarders/bbf-l2-fwd:forwarder[bbf-l2-fwd:ports/bbf-l2-fwd:port/sub-interface =  current()]/bbf-l2-fwd:flooding-policies/bbf-l2-fwd:flooding-policies-profile])=1
      and
      count(/bbf-l2-fwd:forwarding/bbf-l2-fwd:split-horizon-profiles/bbf-l2-fwd:split-horizon-profile[bbf-l2-fwd:name = /bbf-l2-fwd:forwarding/bbf-l2-fwd:forwarders/bbf-l2-fwd:forwarder[bbf-l2-fwd:ports/bbf-l2-fwd:port/sub-interface = current()]/bbf-l2-fwd:split-horizon-profiles/bbf-l2-fwd:split-horizon-profile])=1"{
      error-message "multicast-network-interface must attach RB forward";
    }
  }
}  
    
  deviation "/igmp-config:multicast/igmp-config:mgmd/igmp-config:multicast-vpn/igmp-config:multicast-network-interface"{
    deviate add{
      must "count(/igmp-config:multicast/igmp-config:mgmd/igmp-config:multicast-vpn/igmp-config:multicast-network-interface) <= /cap:capabilities/cap:capability[cap:cap-name='MAX_NETWORK_INTERFACE']/cap:cap-def/cap:running-count"{
      error-message "maximum number of multicast-network-interface reached";
    }
  } 
}*/

/* deviation "/igmp-config:multicast/igmp-config:mgmd/igmp-config:multicast-vpn/igmp-config:multicast-subscriber-interface/igmp-config:interface-name"{
    deviate add{
      must "count(/igmp-config:multicast/igmp-config:mgmd/igmp-config:multicast-vpn/igmp-config:multicast-subscriber-interface[igmp-config:interface-name = /if:interfaces/if:interface[bbf-subif:subif-lower-layer/bbf-subif:interface = /if:interfaces/if:interface[bbf-ptmif:ptmif-lower-layer/bbf-ptmif:interface = /if:interfaces/if:interface[bbf-if-port-ext:port-layer-if = /if:interfaces/if:interface[if:name = /if:interfaces/if:interface[if:name = /if:interfaces/if:interface[if:name = current()]/bbf-subif:subif-lower-layer/bbf-subif:interface]/bbf-ptmif:ptmif-lower-layer/bbf-ptmif:interface]/bbf-if-port-ext:port-layer-if]/if:name]/if:name]/if:name]) <= /cap:capabilities/cap:capability[cap:cap-name='MAX_CHANNELS_PER_LINE']/cap:cap-def/cap:running-count"{
      error-message "maximum number of multicast-subscriber-interface reached";
      }
    }
  }*/
  
  deviation "/igmp-config:multicast/igmp-config:mgmd/igmp-config:multicast-vpn/igmp-config:multicast-channel/igmp-config:group-address"{
    deviate add{
      must "(number(substring-before(current(),'.'))*256*256*256 + number(substring-before(substring-after(current(),'.'),'.'))*256*256 + number(substring-before(substring-after(substring-after(current(),'.'),'.'),'.'))*256 + number(substring-after(substring-after(substring-after(current(),'.'),'.'),'.')) > 224*256*256*256 + 2) 
      and (number(substring-before(current(),'.'))*256*256*256 + number(substring-before(substring-after(current(),'.'),'.'))*256*256 + number(substring-before(substring-after(substring-after(current(),'.'),'.'),'.'))*256 + number(substring-after(substring-after(substring-after(current(),'.'),'.'),'.')) < 240*256*256*256)
      and current() != '224.0.0.22'
      "{
      error-message "group-address can not be special or incorrect IP address";
      }     
    }
  }

  deviation "/igmp-config:multicast/igmp-config:mgmd/igmp-config:multicast-vpn/igmp-config:multicast-channel/igmp-config:group-address-end"{
    deviate add{
      must "((number(substring-before(current(),'.'))*256*256*256 + number(substring-before(substring-after(current(),'.'),'.'))*256*256 + number(substring-before(substring-after(substring-after(current(),'.'),'.'),'.'))*256 + number(substring-after(substring-after(substring-after(current(),'.'),'.'),'.')) < 224*256*256*256 + 22)
      or ((number(substring-before(current(),'.'))*256*256*256 + number(substring-before(substring-after(current(),'.'),'.'))*256*256 + number(substring-before(substring-after(substring-after(current(),'.'),'.'),'.'))*256 + number(substring-after(substring-after(substring-after(current(),'.'),'.'),'.')) > 224*256*256*256 + 22) and (number(substring-before(current()/../igmp-config:group-address,'.'))*256*256*256 + number(substring-before(substring-after(current()/../igmp-config:group-address,'.'),'.'))*256*256 + number(substring-before(substring-after(substring-after(current()/../igmp-config:group-address,'.'),'.'),'.'))*256 + number(substring-after(substring-after(substring-after(current()/../igmp-config:group-address,'.'),'.'),'.')) > 224*256*256*256 + 22))) 
      and (number(substring-before(current(),'.'))*256*256*256 + number(substring-before(substring-after(current(),'.'),'.'))*256*256 + number(substring-before(substring-after(substring-after(current(),'.'),'.'),'.'))*256 + number(substring-after(substring-after(substring-after(current(),'.'),'.'),'.')) < 240*256*256*256)
      and current() != '224.0.0.22'
      "{
      error-message "group-address-end can not be special or incorrect IP address";
      }     
    }
  }

  deviation "/igmp-config:multicast/igmp-config:mgmd/igmp-config:multicast-vpn/igmp-config:multicast-channel/igmp-config:group-address-end"{
    deviate add{
      must "current() = '0.0.0.0'
      or (current()/../igmp-config:group-address and ((number(substring-before(current(),'.'))*256*256*256 + number(substring-before(substring-after(current(),'.'),'.'))*256*256 + number(substring-before(substring-after(substring-after(current(),'.'),'.'),'.'))*256 + number(substring-after(substring-after(substring-after(current(),'.'),'.'),'.'))) > (number(substring-before(current()/../igmp-config:group-address,'.'))*256*256*256 + number(substring-before(substring-after(current()/../igmp-config:group-address,'.'),'.'))*256*256 + number(substring-before(substring-after(substring-after(current()/../igmp-config:group-address,'.'),'.'),'.'))*256 + number(substring-after(substring-after(substring-after(current()/../igmp-config:group-address,'.'),'.'),'.')))))
      "{
      error-message "group-address-end must be greater than group-address";
      }     
    }
  }
  
  deviation "/igmp-config:multicast/igmp-config:mgmd/igmp-config:multicast-vpn/igmp-config:multicast-channel/igmp-config:source-address"{
    deviate add{
      default "0.0.0.0";
    }
    deviate add{
      must "(number(substring-before(current(),'.'))*256*256*256 + number(substring-before(substring-after(current(),'.'),'.'))*256*256 + number(substring-before(substring-after(substring-after(current(),'.'),'.'),'.'))*256 + number(substring-after(substring-after(substring-after(current(),'.'),'.'),'.')) >= 0)
      and (number(substring-before(current(),'.'))*256*256*256 + number(substring-before(substring-after(current(),'.'),'.'))*256*256 + number(substring-before(substring-after(substring-after(current(),'.'),'.'),'.'))*256 + number(substring-after(substring-after(substring-after(current(),'.'),'.'),'.')) <= 223*256*256*256 + 256*256*256 + 256*256 + 256)"{
      error-message "source address can not be D class IP";
      }
    }      
  }
  
/*  deviation "/igmp-config:multicast/igmp-config:mgmd/igmp-config:multicast-vpn/igmp-config:multicast-channel/igmp-config:source-address"{
    deviate add{
      must "current() = '0.0.0.0'
      or 
      not (current()/../../igmp-config:multicast-proxy-profile-name)
      or
      /igmp-config:multicast/igmp-config:mgmd/igmp-config:multicast-proxy-profile[igmp-config:name = current()/../../igmp-config:multicast-proxy-profile-name]/igmp-config:interface-version != 'IGMPv2'"{
      error-message "v2 source address must be 0.0.0.0";
      }
    }
  }*/
  
// WORKAROUND FNMS-17404
//  deviation "/igmp-config:multicast/igmp-config:mgmd/igmp-config:multicast-vpn/igmp-config:multicast-channel"{
//    deviate add{
//      must "(current()/igmp-config:group-address-end = '0.0.0.0'
//      and count(/igmp-config:multicast/igmp-config:mgmd/igmp-config:multicast-vpn/igmp-config:multicast-channel[igmp-config:name != current()/igmp-config:name and (igmp-config:source-address = '0.0.0.0' or igmp-config:source-address = current()/igmp-config:source-address or igmp-config:igmp-network-interface-name = current()/igmp-config:igmp-network-interface-name) and igmp-config:group-address-end != '0.0.0.0'
//      and ((number(substring-before(current()/igmp-config:group-address,'.'))*256*256*256 + number(substring-before(substring-after(current()/igmp-config:group-address,'.'),'.'))*256*256 + number(substring-before(substring-after(substring-after(current()/igmp-config:group-address,'.'),'.'),'.'))*256 + number(substring-after(substring-after(substring-after(current()/igmp-config:group-address,'.'),'.'),'.'))) <= (number(substring-before(igmp-config:group-address-end,'.'))*256*256*256 + number(substring-before(substring-after(igmp-config:group-address-end,'.'),'.'))*256*256 + number(substring-before(substring-after(substring-after(igmp-config:group-address-end,'.'),'.'),'.'))*256 + number(substring-after(substring-after(substring-after(igmp-config:group-address-end,'.'),'.'),'.'))))
//      and ((number(substring-before(current()/igmp-config:group-address,'.'))*256*256*256 + number(substring-before(substring-after(current()/igmp-config:group-address,'.'),'.'))*256*256 + number(substring-before(substring-after(substring-after(current()/igmp-config:group-address,'.'),'.'),'.'))*256 + number(substring-after(substring-after(substring-after(current()/igmp-config:group-address,'.'),'.'),'.'))) >= (number(substring-before(igmp-config:group-address,'.'))*256*256*256 + number(substring-before(substring-after(igmp-config:group-address,'.'),'.'))*256*256 + number(substring-before(substring-after(substring-after(igmp-config:group-address,'.'),'.'),'.'))*256 + number(substring-after(substring-after(substring-after(igmp-config:group-address,'.'),'.'),'.'))))]) = 0
//      and count(/igmp-config:multicast/igmp-config:mgmd/igmp-config:multicast-vpn/igmp-config:multicast-channel[igmp-config:name != current()/igmp-config:name and (igmp-config:source-address = '0.0.0.0' or igmp-config:source-address = current()/igmp-config:source-address or igmp-config:igmp-network-interface-name = current()/igmp-config:igmp-network-interface-name) and igmp-config:group-address-end = '0.0.0.0' and igmp-config:group-address = current()/igmp-config:group-address]) = 0)
//      or
//      (current()/igmp-config:group-address-end != '0.0.0.0'
//      and count(/igmp-config:multicast/igmp-config:mgmd/igmp-config:multicast-vpn/igmp-config:multicast-channel[igmp-config:name != current()/igmp-config:name and (igmp-config:source-address = '0.0.0.0' or igmp-config:source-address = current()/igmp-config:source-address or igmp-config:igmp-network-interface-name = current()/igmp-config:igmp-network-interface-name) and igmp-config:group-address-end != '0.0.0.0'
//      and ((number(substring-before(igmp-config:group-address-end,'.'))*256*256*256 + number(substring-before(substring-after(igmp-config:group-address-end,'.'),'.'))*256*256 + number(substring-before(substring-after(substring-after(igmp-config:group-address-end,'.'),'.'),'.'))*256 + number(substring-after(substring-after(substring-after(igmp-config:group-address-end,'.'),'.'),'.'))) >= (number(substring-before(current()/igmp-config:group-address,'.'))*256*256*256 + number(substring-before(substring-after(current()/igmp-config:group-address,'.'),'.'))*256*256 + number(substring-before(substring-after(substring-after(current()/igmp-config:group-address,'.'),'.'),'.'))*256 + number(substring-after(substring-after(substring-after(current()/igmp-config:group-address,'.'),'.'),'.'))))
//      and ((number(substring-before(igmp-config:group-address,'.'))*256*256*256 + number(substring-before(substring-after(igmp-config:group-address,'.'),'.'))*256*256 + number(substring-before(substring-after(substring-after(igmp-config:group-address,'.'),'.'),'.'))*256 + number(substring-after(substring-after(substring-after(igmp-config:group-address,'.'),'.'),'.'))) <= (number(substring-before(current()/igmp-config:group-address-end,'.'))*256*256*256 + number(substring-before(substring-after(current()/igmp-config:group-address-end,'.'),'.'))*256*256 + number(substring-before(substring-after(substring-after(current()/igmp-config:group-address-end,'.'),'.'),'.'))*256 + number(substring-after(substring-after(substring-after(current()/igmp-config:group-address-end,'.'),'.'),'.'))))]) = 0
//      and count(/igmp-config:multicast/igmp-config:mgmd/igmp-config:multicast-vpn/igmp-config:multicast-channel[igmp-config:name != current()/igmp-config:name and (igmp-config:source-address = '0.0.0.0' or igmp-config:source-address = current()/igmp-config:source-address or igmp-config:igmp-network-interface-name = current()/igmp-config:igmp-network-interface-name) and igmp-config:group-address-end = '0.0.0.0'
//      and ((number(substring-before(igmp-config:group-address,'.'))*256*256*256 + number(substring-before(substring-after(igmp-config:group-address,'.'),'.'))*256*256 + number(substring-before(substring-after(substring-after(igmp-config:group-address,'.'),'.'),'.'))*256 + number(substring-after(substring-after(substring-after(igmp-config:group-address,'.'),'.'),'.'))) >= (number(substring-before(current()/igmp-config:group-address,'.'))*256*256*256 + number(substring-before(substring-after(current()/igmp-config:group-address,'.'),'.'))*256*256 + number(substring-before(substring-after(substring-after(current()/igmp-config:group-address,'.'),'.'),'.'))*256 + number(substring-after(substring-after(substring-after(current()/igmp-config:group-address,'.'),'.'),'.'))))
//      and ((number(substring-before(igmp-config:group-address,'.'))*256*256*256 + number(substring-before(substring-after(igmp-config:group-address,'.'),'.'))*256*256 + number(substring-before(substring-after(substring-after(igmp-config:group-address,'.'),'.'),'.'))*256 + number(substring-after(substring-after(substring-after(igmp-config:group-address,'.'),'.'),'.'))) <= (number(substring-before(current()/igmp-config:group-address-end,'.'))*256*256*256 + number(substring-before(substring-after(current()/igmp-config:group-address-end,'.'),'.'))*256*256 + number(substring-before(substring-after(substring-after(current()/igmp-config:group-address-end,'.'),'.'),'.'))*256 + number(substring-after(substring-after(substring-after(current()/igmp-config:group-address-end,'.'),'.'),'.'))))]) = 0)
//      "{
//      error-message "group address can not be overlapped";
//      }
//    }
  }
  
  
}
