module bbf-l2-forwarding-forwarders-dev {

/* MODULE-HEADER part-1*/
/* =================== */
  namespace "urn:broadband-forum-org:yang:" +
            "bbf-l2-forwarding-forwarders-dev";

  prefix bbf-l2-fwd-dev;


  import bbf-l2-forwarding {
    prefix bbf-l2-fwd;
  }
  
 import ietf-interfaces {
    prefix if;
  }

  import bbf-sub-interface-tagging{
        prefix bbf-subif-tag;
  }

  import bbf-sub-interfaces{
        prefix bbf-subif;
  } 
  
  import bbf-interfaces-performance-management{
    prefix bbf-if-pm;
  }  
  organization
    "NOKIA";

  contact
    " ";

  description
    " ";

/* REVISION */
/* ======== */
  revision 2016-11-28 {
    description
      "Initial revision.";
    reference
      "TBD";
  }

/* DEFINITION */
/* ========== */
	deviation "/if:interfaces/if:interface/bbf-subif:frame-processing" {
		deviate add{
			must "../type != 'bbfift:vlan-sub-interface'
			    or
                ((../bbf-l2-fwd:interface-usage/bbf-l2-fwd:interface-usage = 'network-port' 
                and				
			    ../bbf-if-pm:performance/bbf-if-pm:enable = 'false')
				or
				../bbf-l2-fwd:interface-usage/bbf-l2-fwd:interface-usage = 'user-port')
		    "{
				error-message "Enable PM counter on vlan-sub-interface(network port) and it should be deny";
			}
		}
	}
    deviation "/if:interfaces/if:interface/bbf-l2-fwd:interface-usage/bbf-l2-fwd:interface-usage" {
		deviate add{
			must "../../type != 'bbfift:vlan-sub-interface' or current() != 'user-port' or
			(/if:interfaces/if:interface[if:name = current()/../../bbf-subif:subif-lower-layer/bbf-subif:interface]/type = 'bbfift:ptm') "{
			   error-message "The user side vlan-sub-interface's lower interface must be PTM";
			}
		}
	}
	
	/*deviation "/if:interfaces/if:interface" {
		deviate add{
			must "current()/type != 'bbfift:vlan-sub-interface' or current()/bbf-l2-fwd:interface-usage/bbf-l2-fwd:interface-usage != 'user-port' or
			(/if:interfaces/if:interface[if:name = current()/bbf-subif:subif-lower-layer/bbf-subif:interface]/type = 'bbfift:ptm') "{
			   error-message "The user side vlan-sub-interface's lower interface must be PTM";
			}
		}
	}*/

	/*Match pbit value other than "any" will be rejected*/
	deviation "/if:interfaces/if:interface/bbf-subif:frame-processing/bbf-subif:ingress-rule/bbf-subif:rule/bbf-subif:flexible-match/bbf-subif-tag:match-criteria/bbf-subif-tag:vlan-tag-match-type/bbf-subif-tag:vlan-tagged/bbf-subif-tag:tag/bbf-subif-tag:dot1q-tag/bbf-subif-tag:pbit" {
		deviate add{
			must "current() = 'any'"{
				error-message "Match pbit of vlan-sub-interface tagged rule value other than 'any' will be rejected";
			}
		}
	}
	
	/*Match dei value other than "any" will be rejected*/
	deviation "/if:interfaces/if:interface/bbf-subif:frame-processing/bbf-subif:ingress-rule/bbf-subif:rule/bbf-subif:flexible-match/bbf-subif-tag:match-criteria/bbf-subif-tag:vlan-tag-match-type/bbf-subif-tag:vlan-tagged/bbf-subif-tag:tag/bbf-subif-tag:dot1q-tag/bbf-subif-tag:dei" {
		deviate add{
			must "current() = 'any'"{
				error-message "Match dei of vlan-sub-interface tagged rule value other than 'any' will be rejected";
			} 
		}
	}	
	
	/* The VLAN tag in match criteria with range or "any VLAN-ID" will be rejected */
	deviation "/if:interfaces/if:interface/bbf-subif:frame-processing/bbf-subif:ingress-rule/bbf-subif:rule/bbf-subif:flexible-match/bbf-subif-tag:match-criteria" {
		deviate add{
			must "(contains(current()/bbf-subif-tag:tag/bbf-subif-tag:dot1q-tag/bbf-subif-tag:vlan-id,'priority-tagged'))
		      or
			      (not(contains(current()/bbf-subif-tag:tag/bbf-subif-tag:dot1q-tag/bbf-subif-tag:vlan-id,'-')) 
			      and not(contains(current()/bbf-subif-tag:tag/bbf-subif-tag:dot1q-tag/bbf-subif-tag:vlan-id,','))
				  and not(contains(current()/bbf-subif-tag:tag/bbf-subif-tag:dot1q-tag/bbf-subif-tag:vlan-id,'any')))
            "{
			   error-message "The vlan-sub-interface VLAN tag in match criteria with range or 'any VLAN-ID' will be rejected";
			}
		}
	}
		
	deviation "/bbf-l2-fwd:forwarding/bbf-l2-fwd:split-horizon-profiles/bbf-l2-fwd:split-horizon-profile/bbf-l2-fwd:split-horizon" {
		deviate add{
			must "current()/bbf-l2-fwd:in-interface-usage = 'user-port'
			      and
                  current()/bbf-l2-fwd:out-interface-usage = 'user-port'				  
            "{
			   error-message "Only allow to configure block user 2 user traffic, other configurations are rejected";
			}
		}
	}		


}
