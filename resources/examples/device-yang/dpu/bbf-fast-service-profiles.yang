submodule bbf-fast-service-profiles {
//  yang-version 1.1;
  belongs-to bbf-fast {
    prefix bbf-fast;
  }

  import bbf-yang-types {
    prefix bbf-yang;
  }

  include bbf-fast-base;

  /* Profile bodies */
  include bbf-fast-data-rate-profile-body;


  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for
     managing FAST service profiles.

     Copyright (c) 2016, 2017 Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-??-??.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef downstream-data-rate-profile-ref {
    type leafref {
      path '/bbf-fast:fast/bbf-fast:service/bbf-fast:downstream-'
         + 'data-rate-profile/bbf-fast:name';
    }
    description
      "Used to reference a downstream data rate profile";
  }

  typedef upstream-data-rate-profile-ref {
    type leafref {
      path '/bbf-fast:fast/bbf-fast:service/bbf-fast:upstream-data-'
         + 'rate-profile/bbf-fast:name';
    }
    description
      "Used to reference an upstream data rate profile";
  }

  typedef low-power-data-rate-profile-ref {
    type leafref {
      path '/bbf-fast:fast/bbf-fast:service/bbf-fast:low-power-'
         + 'data-rate-profile/bbf-fast:name';
    }
    description
      "Used to reference a low power data rate profile";
  }

  augment '/bbf-fast:fast/bbf-fast:service' {
    description
      "Data nodes for service-related configuration profiles.";

    list downstream-data-rate-profile {
      key "name";
      description
        "A list of downstream data-rate profiles.";

      leaf name {
        type bbf-yang:string-ascii64;
        description
          "Uniquely identifies the profile.";
      }

      uses data-rate-profile;
    }

    list upstream-data-rate-profile {
      key "name";
      description
        "A list of upstream data-rate profiles.";

      leaf name {
        type bbf-yang:string-ascii64;
        description
          "Uniquely identifies the profile.";
      }

      uses data-rate-profile;
    }

    list low-power-data-rate-profile {
      key "name";
      description
        "A list of low power data rate profiles.";

      leaf name {
        type bbf-yang:string-ascii64;
        description
          "Uniquely identifies the profile.";
      }

      uses low-power-data-rate-profile;
    }
  }
}
