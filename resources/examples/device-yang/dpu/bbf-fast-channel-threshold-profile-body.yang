submodule bbf-fast-channel-threshold-profile-body {
//  yang-version 1.1;
  belongs-to bbf-fast {
    prefix bbf-fast;
  }

  include bbf-fast-perf-types;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for
     managing channel threshold profiles.

     Copyright (c) 2016, 2017 Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-??-??.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping channel-thresholds {
    description
      "Performance parameters that have corresponding thresholds
       used to issue reports";

    leaf code-violations-threshold {
      type uint32;
      units "1 second";
      default "0";
      description
        "Threshold for the count of the cyclic redundancy check 
         anomalies (crc). A special value (0) indicates the
         threshold is disabled. The cyclic redundancy check anomaly
         (crc) is defined in clause 11.3.1.1/G.9701.";
      reference
        "ITU-T G.997.2 clause 7.8.4 (CURR/PREV_NE/FE_15/24_CV);
         ITU-T G.997.2 clause 8.2 (THRESHOLD_NE/FE_15/24_CV)";
    }

    leaf uncorrectable-dtus-threshold {
      type uint32;
      units "1 second";
      default "0";
      description
        "Threshold for the count of the uncorrected DTU anomalies
         (rtx-uc). A special value (0) indicates the threshold is
         disabled. The uncorrected DTU anomaly (rtx-uc) is defined
         in clause 11.3.1.1/G.9701.";
      reference
        "ITU-T G.997.2 clause 7.8.6 (CURR/PREV_NE/FE_15/24_RTXUC);
         ITU-T G.997.2 clause 8.2 (THRESHOLD_NE/FE_15/24_RTXUC)";
    }

    leaf retransmitted-dtus-threshold {
      type uint32;
      units "1 second";
      default "0";
      description
        "Threshold for the count of the retransmitted DTU anomalies
         (rtx-tx). A special value (0) indicates the threshold is
         disabled. The retransmitted DTU anomaly (rtx-tx) is defined
         in clause 11.3.1.1/G.9701.";
      reference
        "ITU-T G.997.2 clause 7.8.7 (CURR/PREV_NE/FE_15/24_RTXTX);
         ITU-T G.997.2 clause 8.2 (THRESHOLD_NE/FE_15/24_RTXTX)";
    }
  }
}
