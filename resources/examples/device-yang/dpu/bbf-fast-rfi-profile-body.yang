submodule bbf-fast-rfi-profile-body {
//  yang-version 1.1;
  belongs-to bbf-fast {
    prefix bbf-fast;
  }

  include bbf-fast-line-spectrum-profile-body;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for
     managing RFI profiles.

     Copyright (c) 2016, 2017 Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-??-??.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping rfibands {
    description
      "Parameters associated with Radio Frequency Interference
       bands";

    list rfiband {
      key "start-index";
      max-elements 32;
      description
        "Defines the bands where the PSD shall be reduced as
         specified in G.9701 clause 7.3.1.2.";
      reference
        "ITU-T G.997.2 clause 7.1.2.7 (RFIBANDS); ITU-T G.9701
         Clause 7.3.1.2.";

      uses sub-carrier-range;
    }
  }

  typedef iarbands {
    type bits {
      bit kHz-1800-2000 {
        position 0;
        description
          "International amateur radio band 1800-2000 kHz";
      }
      bit kHz-3500-4000 {
        position 1;
        description
          "International amateur radio band 3500-4000 kHz";
      }
      bit kHz-7000-7300 {
        position 2;
        description
          "International amateur radio band 7000-7300 kHz";
      }
      bit kHz-10100-10150 {
        position 3;
        description
          "International amateur radio band 10100-10150 kHz";
      }
      bit kHz-14000-14350 {
        position 4;
        description
          "International amateur radio band 14000-14350 kHz";
      }
      bit kHz-18068-18168 {
        position 5;
        description
          "International amateur radio band 18068-18168 kHz";
      }
      bit kHz-21000-21450 {
        position 6;
        description
          "International amateur radio band 21000-21450 kHz";
      }
      bit kHz-24890-24990 {
        position 7;
        description
          "International amateur radio band 24890-24990 kHz";
      }
      bit kHz-28000-29700 {
        position 8;
        description
          "International amateur radio band 28000-29700 kHz";
      }
      bit kHz-50000-54000 {
        position 9;
        description
          "International amateur radio band 50000-54000 kHz";
      }
      bit kHz-69900-70500 {
        position 10;
        description
          "International amateur radio band 70000-70500 kHz";
      }
      bit kHz-144000-148000 {
        position 11;
        description
          "International amateur radio band 144000-148000 kHz";
      }
      bit kHz-5351.5-5366.5 {
        position 12;
        description
          "International amateur radio band 5351.5-5366.5 kHz";
      }
    }
    description
      "Defines for each International Amateur Radio (IAR) band
       whether transmit PSD reduction is enabled or disabled in that
       band.";
    reference
      "ITU-T G.997.2 clause 7.1.2.8 (IARBANDS); ITU-T G.9701 clause
       7.3.1.2 and 12.3.2.1.1; ITU-T G.994.1 Table 11.70.8 and
       11.70.8.1.";
  }

  grouping rfi-profile {
    description
      "Defines the parameters contained in an RFI profile.";

    uses rfibands;

    leaf iarbands {
      type iarbands;
      default "";
      description
        "Defines for each International Amateur Radio (IAR) band
         whether transmit PSD reduction is enabled or disabled in
         that band.";
      reference
        "ITU-T G.997.2 clause 7.1.2.8 (IARBANDS); ITU-T G.9701
         clause 7.3.1.2 and 12.3.2.1.1; ITU-T G.994.1 Table 11.70.8
         and 11.70.8.1.";
    }
  }
}
