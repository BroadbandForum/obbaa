module bbf-sub-interface-tagging {
  //yang-version 1.1;
  namespace "urn:bbf:yang:bbf-sub-interface-tagging";

  prefix bbf-subif-tag;

  import ietf-interfaces {
    prefix if;
  }

  import bbf-dot1q-types {
    prefix bbf-dot1qt;
  }

  import bbf-sub-interfaces {
    prefix bbf-subif;
  }

  import bbf-frame-classification {
    prefix bbf-classif;
  }

  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "A collection of management objects for defining the ingress and 
     egress tagging of a sub-interface.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2016-05-30 {
    description
      "Initial revision.
       * Approval Date:    see revision date above.
       * Publication Date: yyyy-mm-dd.";
    reference
      "TR-383: Common YANG Modules
               <https://www.broadband-forum.org/technical/download/
                        TR-383.pdf>";
  }

  grouping pbit-marking {
    description
      "The Priority bits (3 bits) of a VLAN tag.
       These PBIT bits are in the VLAN tag next to the DEI (1 bit) 
       and the VLAN-ID (12 bits).";

    choice pbit-action {
      mandatory true;
      description
        "Defines how to write the pbit.";

      case write-pbit-0 {
        description
          "Tagged and priority-tagged frames contain a PBIT.
           Untagged frames do not contain a PBIT.
           Write-pbit-0 provides a simple method to identify what 
           PBIT shall be inserted in the output frame that can be 
           applied to all frame types. More advanced methods can be 
           provided via other pbit-action cases.";

        leaf write-pbit-0 {
          type empty;
          description
            "Push PBIT=0 in the tag.";
        }
      }

      case copy-pbit-from-input-or-0 {
        description
          "Copy from the specified input tag, or write PBIT=0 if the
           input tag does not exist";

        leaf pbit-from-tag-index {
          type bbf-classif:tag-index;
          description
            "Specifies from which tag the PBIT bits shall be copied.";
        }
      }
    }
  }

  grouping dei-marking {
    description
      "The Drop Eligibility Indicator bit (1 bit) of a VLAN tag.
       This bit is in the VLAN tag next to the PBIT (3 bits) and the 
       VLAN-ID (12 bits). ";

    choice dei-action {
      mandatory true;
      description
        "Defines how to write the DEI bit.";

      case write-dei-0 {
        description
          "Tagged and priority-tagged frames contain a DEI bit.
           Untagged frames do not contain a DEI bit.
           Write-dei-0 provides a simple method to identify what 
           DEI shall be inserted in the output frame that can be 
           applied to all frame types. More advanced methods can be 
           provided via other dei-action cases.";

        leaf write-dei-0 {
          type empty;
          description
            "Push DEI=0 in the tag.";
        }
      }

      case copy-dei-from-input-or-0 {
        description
          "Copy DEI from the specified input tag, or write DEI=0 if 
           the input tag does not exist.";

        leaf dei-from-tag-index {
          type bbf-classif:tag-index;

          description
            "Specifies from which tag the DEI bit shall be copied.";
        }
      }
    }
  }

  grouping dot1q-tag {
    description
      "Grouping to allow configuration to identify a single 802.1Q 
       VLAN tag.";

    container dot1q-tag {
      description
        "Identifies an 802.1Q VLAN tag with an explicit tag-type and 
         a single VLAN-ID.";

      leaf tag-type {
        type bbf-dot1qt:dot1q-tag-type;

        mandatory true;

        description
          "VLAN tag type.";
      }

      leaf vlan-id {
        type bbf-dot1qt:vlan-id-or-0;

        mandatory true;

        description
          "The VLAN-ID or the value 0 (priority-tagged).";
      }

      uses pbit-marking;
      uses dei-marking;
    }
  }

  grouping flexible-rewrite {
    description
      "Tag manipulation actions.";

    leaf pop-tags {
      type uint8 {
        range "0..2";
      }

      default "0";

      description
        "The number of tags to pop (or translate if used in 
         conjunction with push-tags)";
    }

    list push-tag {
      key "index";
      max-elements "2";

      description
        "The number of tags to push (or translate if used in 
         conjunction with pop-tags)";
      /*
       * Server should order by increasing index.
       */
      leaf index {
        type bbf-classif:tag-index;

        /*
         * Only allow a push of an inner tag if an outer tag is also
         * being pushed.
         */
        must '. = 0 or count(../../push-tag[index = 0]/index) > 0' {
          error-message
            "An inner tag can only be pushed if an outer tag is also 
             specified";

          description
            "Only allow a push of an inner tag if an outer tag is 
             also being pushed";
        }
        description
          "The index into the tag stack";
      }

      uses dot1q-tag;
    }
  }

  augment '/if:interfaces/if:interface/bbf-subif:frame-processing/'
        + 'bbf-subif:ingress-rule/bbf-subif:rule/bbf-subif:'
        + 'flexible-match' {

    /*when 'derived-from-or-self(../../../../if:type, 
          "bbfift:vlan-sub-interface")'
    {
      description
        "Augments the general flexible-match container with specific 
         VLAN match criteria.";
    }*/

    description
      "Augments the general flexible-match container with specific 
       vlan match criteria.";

    container match-criteria {
      description
        "This container collects match criteria";

      uses bbf-classif:frame-destination-match;

      uses bbf-classif:multiple-vlan-tag-match;

      uses bbf-classif:ether-type-match;

      uses bbf-classif:protocol-match;
    }
  }

  augment '/if:interfaces/if:interface/bbf-subif:frame-processing/'
        + 'bbf-subif:ingress-rule/bbf-subif:rule/bbf-subif:'
        + 'flexible-match/match-criteria/vlan-tag-match-type/vlan-'
        + 'tagged/tag' {
    /*when 'derived-from-or-self(/../../../../../../if:type, 
          "bbfift:vlan-sub-interface")'
    {
      description
        "Defines match criteria for all the fields of VLAN tags, being
         the TPID, the VLAN-ID, the PBIT, and the DEI fields.";
    }*/
    

    description
      "Defines match criteria for all the fields of VLAN tags, being 
       the TPID, the VLAN-ID, the PBIT, and the DEI fields.";

    uses bbf-classif:dot1q-tag-ranges-or-any;
  }

  augment '/if:interfaces/if:interface/bbf-subif:frame-processing/'
        + 'bbf-subif:ingress-rule/bbf-subif:rule/bbf-subif:ingress-'
        + 'rewrite' {
    /*when 'derived-from-or-self(../../../../if:type,
          "bbfift:vlan-sub-interface")'
    {
      description
        "Augments the general ingress-rewrite container with specific 
         vlan rewrite actions.";
    }*/

    description
      "Augments the general ingress-rewrite container with specific 
       vlan rewrite actions.";

    uses flexible-rewrite;
  }



  augment '/if:interfaces/if:interface/bbf-subif:frame-processing/'
        + 'bbf-subif:egress-rewrite' {

    /*when 'derived-from-or-self(../../if:type,
          "bbfift:vlan-sub-interface")'
    {
      description
        "Augments the general egress-rewrite container with specific 
         vlan rewrite actions.";
    }*/

    description
      "Augments the general egress-rewrite container with specific 
       vlan rewrite actions.";

    uses flexible-rewrite;
  }
}
