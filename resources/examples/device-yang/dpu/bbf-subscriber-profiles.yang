module bbf-subscriber-profiles {
  //yang-version 1.1;
  namespace "urn:bbf:yang:bbf-subscriber-profiles";

  prefix bbf-subprof;

  import ietf-interfaces {
    prefix if;
  }

  import ietf-system {
    prefix sys;
  }

  import bbf-yang-types {
    prefix bbf-yang;
  }

  import bbf-if-type {
    prefix bbfift;
  }

  import bbf-l2-forwarding {
    prefix bbf-l2-fwd;
  }

  import bbf-subscriber-types {
    prefix bbf-subtype;
  }

  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "A YANG Data Model for managing subscriber profiles.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2016-07-06 {
    description
      "Initial revision.
       * Approval Date:    see revision date above.
       * Publication Date: yyyy-mm-dd.";

    reference
      "TR-383: Common YANG Modules
               <https://www.broadband-forum.org/technical/download/
                        TR-383.pdf>";
  }

  typedef subscriber-profile-ref {
    type leafref {
      path '/bbf-subprof:subscriber-profiles/bbf-subprof:'
         + 'subscriber-profile/bbf-subprof:name';
    }
    description
      "A reference to a subscriber profile.";
  }

  container subscriber-profiles {
    description
      "Subscriber configuration profile.";

    list subscriber-profile {
      key "name";

      description
        "List containing the parameters for a subscriber profile.
         Various protocols need to insert strings in options / 
         sub-tags. These strings are used to identify the subscriber. 
         This insertion can be enabled per protocol per 
         vlan-sub-interface. Identifying the subscriber is independent
         of the protocol and most likely identical for all 
         vlan-sub-interfaces on top of the same physical line.
         Therefore this data is provided in a profile.";

      leaf name {
        type bbf-yang:string-ascii64;
        description
          "Name of the profile.";
      }

      leaf circuit-id {
        type bbf-subtype:string-ascii63-or-empty;
        default "";
        description
          "The circuit-id string to be inserted in the subscriber
           management protocol packets.
           The string is the actual value inserted in the sub-tag.";
        reference
          "TR-178i1 - R117 and TR-177i1 - R08.";
      }

      leaf remote-id {
        type bbf-subtype:string-ascii63-or-empty;
        default "";
        description
          "The remote-id string to be inserted in the subscriber
           management protocol packets.
           The string is the actual value inserted in the sub-tag.";
        reference
          "TR-178i1 R120 and TR-177i1 - R10.";
      }

      leaf subscriber-id {
        type bbf-subtype:string-ascii63-or-empty;
        default "";
        description
          "A subcriber-id string to be inserted in the subscriber
           management protocol packets.
           The subscriber-id carries a value that can be 
           independent of the physical network configuration 
           through which the subscriber is connected. This 
           value complements, and might well be used in 
           addition to the network-based information.";
        reference
          "RFC 4580 - Section 2.";
      }
    }
  }

  augment '/if:interfaces/if:interface' {
    /*when 'derived-from-or-self (if:type, "bbfift:vlan-sub-interface")
          and bbf-l2-fwd:interface-usage/bbf-l2-fwd:interface-usage !=
          network-port ' { 
      description
        "Applies only to vlan-sub-interfaces that are not 
         network-ports.";
    } */

    description
      "Additions for subscriber management on the 
       vlan-sub-interface.";

    container subscriber-profile {
      description
        "Subscriber configuration parameters.";

      leaf profile {
        type subscriber-profile-ref;
        description
          "Reference to a subcriber configuration profile.
           A profile is optional because it is possible that 
           subscriber identification is always generated according to 
           a syntax.";
      }
    }
  }

  augment '/sys:system' {
    description
      "Augment the system with generic subscriber management 
       objects.";

    container subscriber-management {
      description
        "Subscriber management system data.";

      leaf access-node-id {
        type bbf-subtype:string-ascii63-or-empty;

        default "access-node";

        description
          "Access-node-id. This string will be inserted in case the 
           keyword Access_Node_ID is part of the syntax according 
           which a subscriber identification string shall be 
           generated.";
      }
    }
  }
}
