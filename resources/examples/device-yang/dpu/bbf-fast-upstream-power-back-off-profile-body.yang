submodule bbf-fast-upstream-power-back-off-profile-body {
//  yang-version 1.1;
  belongs-to bbf-fast {
    prefix bbf-fast;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for
     managing upstream power back off profiles.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping upstream-power-back-off-parameters {
    description
      "Power-back-off-specific configuration parameters.";
    reference
      "ITU-T G.997.2 clause 7.1.2.";

    leaf upbopsd-a {
      type uint16 {
        range "0..4095" {
          description
            "Defines a range equal to 40.00..80.95 dBm/Hz. Uses an
             offset of 40.00 dBm/Hz";
        }
      }
      units "0.01 dBm/Hz";
      default "0";
      description
        "Defines the parameter a for the UPBO reference PSD used to
         compute the upstream power back-off for the upstream
         frequency band.";
      reference
        "ITU-T G.997.2 clause 7.1.2.9 (UPBOPSDA); ITU-T G.9701
         clause 7.3.1.4.";
    }

    leaf upbopsd-b {
      type uint16 {
        range "0..4095" {
          description
            "Defines a range equal to 0..40.95 dBm/Hz.";
        }
      }
      units "0.01 dBm/Hz";
      default "0";
      description
        "Defines the parameter b for the UPBO reference PSD used to
         compute the upstream power back-off for the upstream
         frequency band.";
      reference
        "ITU-T G.997.2 clause 7.1.2.10 (UPBOPSDB); ITU-T G.9701
         clause 7.3.1.4.";
    }

    leaf upbo-upstream-electrical-length {
      type uint16 {
        range "0..1280" {
          description
            "Defines a range equal to 0..128 dB.";
        }
      }
      units "0.1 dB";
      default "0";
      description
        "Defines the electrical length kl0 (expressed in dB at
         1 MHz).";
      reference
        "ITU-T G.997.2 clause 7.1.2.11 (UPBOKL); ITU-T G.9701 clause
         7.3.1.4.2.1.";
    }

    leaf upbo-force-electrical-length {
      type boolean;
      default "false";
      description
        "Defines whether or not the FTU-R is forced to use the
         electrical length kl0 = UPBOKL to compute the UPBOMASK. If
         not forced, the FTUs determine the electrical length kl0.";
      reference
        "ITU-T G.997.2 clause 7.1.2.12 (UPBOKLF); ITU-T G.9701
         clause 7.3.1.4.2.1.";
    }

    leaf upbo-reference-electrical-length {
      type uint16 {
        range "0 | 18..255" {
          description
            "Defines a range equal to 1.8..25.5 dB.
             Special value 0: Use the Equal PSD UPBO method.";
        }
      }
      units "0.1 dB";
      default "0";
      description
        "Defines the UPBO reference electrical length kl0_REF used
         to compute the upstream power back-off for the Equalized
         FEXT UPBO method. If kl0_REF = 0 (special value) then the
         Equal PSD UPBO method is used.";
      reference
        "ITU-T G.997.2 clause 7.1.2.13 (UPBOKLREF); ITU-T G.9701
         clause 7.3.1.4.2.2.";
    }
  }

  grouping upstream-power-back-off-profile {
    description
      "Defines the parameters contained in a power-back-off
       profile.";

    uses upstream-power-back-off-parameters;
  }
}
