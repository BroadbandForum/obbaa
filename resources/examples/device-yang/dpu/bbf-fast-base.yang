submodule bbf-fast-base {
//  yang-version 1.1;
  belongs-to bbf-fast {
    prefix bbf-fast;
  }

  import ietf-interfaces {
    prefix if;
  }

  import bbf-fastdsl {
    prefix bbf-fastdsl;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for
     managing top level FAST configuration and augmenations to
     ietf-interfaces.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  container fast {
    description
      "FAST configuration";

    container service {
      description
        "Service profile configuration";
    }

    container spectrum {
      description
        "Spectrum profile configuration.";
    }

    container quality {
      description
        "Quality profile configuration.";
    }

    container thresholds {
      description
        "Threshold configuration";
    }

    container vectors {
      description
        "Vectors of profiles";
    }
  }

  augment '/if:interfaces/if:interface/bbf-fastdsl:line' {
    when "bbf-fastdsl:configured-mode = 'bbf-fastdsl:mode-fast'" {
      description
        "Applicable when G.fast mode is configured";
    }
    description
      "Data nodes for the configuration of FAST lines.";

    container line {
      presence
        "If present, indicates that the interface is able to operate
         according to ITU-T G.9701.";
      description
        "Line configuration data for FAST interfaces.";
    }
  }

  augment '/if:interfaces-state/if:interface/bbf-fastdsl:line' {
    when "bbf-fastdsl:operational-mode = 'bbf-fastdsl:mode-fast'" {
      description
        "Applicable when G.fast is the current mode of operation";
    }
    description
      "Data nodes for the operational state of FAST lines.";

    container line {
      presence
        "If present, indicates that the interface is able to operate
         according to ITU-T G.9701.";
      description
        "Line state data for FAST interfaces.";

      container channel {
        description
          "Bearer channel state data for FAST interfaces";
      }
    }
  }
}
