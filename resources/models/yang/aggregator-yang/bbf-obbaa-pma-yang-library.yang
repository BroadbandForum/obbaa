module bbf-obbaa-pma-yang-library {
    yang-version 1.1;
    namespace "urn:bbf:yang:obbaa:pma-yang-library";
    prefix pma-yang-library;
    
    import ietf-inet-types {
        prefix inet;
    }
	
    organization
        "broadband_forum";

    contact
        "https://www.broadband-forum.org";

    description
        "PMA YANG library management.";

    revision 2018-06-15 {
        description
            "Initial revision.";
        reference
            "broadband_forum";
    }
    
    container pma-yang-library {
        description "YANG library of PMA.";
        
        action reload {
            description "Reload the YANG library of PMA.";
        }
    }
}
