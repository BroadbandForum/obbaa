module bbf-obbaa-pma-device-config {
    yang-version 1.1;
    namespace "urn:bbf:yang:obbaa:pma-device-config";
    prefix baa-pma-align;

    organization
      "Broadband Forum <https://www.broadband-forum.org>";

    contact
      "Comments or questions about this Broadband Forum YANG module
       should be directed to <mailto:obbaa-leaders@broadband-forum.org>.
      ";

    description
      "This module contains a collection of YANG definitions for 
       supporting alignment operation between BAA and device.
       
       Copyright 2018-2019 Broadband Forum
       
       Licensed under the Apache License, Version 2.0 (the \"License\");
       you may not use this file except in compliance with the License.
       You may obtain a copy of the License at
       
       http://www.apache.org/licenses/LICENSE-2.0
       Unless required by applicable law or agreed to in writing, software
       distributed under the License is distributed on an \"AS IS\" BASIS,
       WITHOUT WARRANTIES OR CONDITIONS OF ANY KIND, either express or implied.
       See the License for the specific language governing permissions and
       limitations under the License. 
      ";
    revision 2018-06-15 {
        description
          "Initial revision.";
        reference
          "broadband_forum";
    }

    identity align-type {
        description
          "Type of align requested of the component.";
    }

    container pma-device-config {
        description
          "Device configuration of PMA.";

        action align {
            description
              "Align device configuration of PMA.";

            input {
                leaf force {
                    type identityref {
                        base align-type;
                    }
                    description
                      "Force align the device configuration.";
                }
            }
        }

        leaf alignment-state {
            type enumeration {
                enum aligned;
                enum mis-aligned;
                enum in-error;
            }
            config false;
            description
              "The leaf indicates whether the device configuration is aligned with the configuration of its PMA";
        }
    }
}
