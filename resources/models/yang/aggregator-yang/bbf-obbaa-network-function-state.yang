module bbf-obbaa-network-function-state {
  yang-version 1.1;
  namespace "urn:bbf:yang:obbaa:network-function-state";
  prefix bbf-baa-nfstate;

  import ietf-yang-types {
    prefix yang;
  }
  
  import bbf-network-function {
    prefix bbf-nf;
  }
  
  import bbf-node-types {
    prefix bbf-node-types;
  }
  
  import bbf-obbaa-network-manager {
    prefix baa-network-manager;
  }
  
  import bbf-yang-types {
    prefix bbf-yang;
  }
  
  organization
    "Broadband Forum <https://www.broadband-forum.org>";
  
  contact
    "Comments or questions about this Broadband Forum YANG module
     should be directed to <mailto:obbaa-leaders@broadband-forum.org>.
    ";
  
  description
    "This module contains a collection of YANG definitions needed to
     report state information about VNFs (Virtual Network Functions)
     in the context of OB-BAA.
     
     Copyright 2022 Broadband Forum
     
     Licensed under the Apache License, Version 2.0 (the \"License\");
     you may not use this file except in compliance with the License.
     You may obtain a copy of the License at
     
     http://www.apache.org/licenses/LICENSE-2.0
     Unless required by applicable law or agreed to in writing, software
     distributed under the License is distributed on an \"AS IS\" BASIS,
     WITHOUT WARRANTIES OR CONDITIONS OF ANY KIND, either express or implied.
     See the License for the specific language governing permissions and
     limitations under the License.";
  
  
  revision 2022-04-04 {
    description
      "Initial revision.";
    reference
      "https://obbaa.broadband-forum.org/";
  }
  
  augment '/baa-network-manager:network-manager' {
    description
      "The state data associated with Network Functions.";
    
    container network-functions-state
    {
      config false;
      description
         "The state data associated with Network Functions.";
      
      uses bbf-nf:virtual-network-functions;
      uses bbf-nf:virtual-network-function-instances;
    }
  }
  
  augment '/baa-network-manager:network-manager/' 
    + 'bbf-baa-nfstate:network-functions-state/'
    + 'bbf-baa-nfstate:virtual-network-function' {
    
    description 
      "Extensions to Virtual Network Function (VNF).";
    
    container hosting-environment {
      description
        "Information about the hosting environment of the Network
        Function.";
     
      /*
      In the future a reference to a hosting environment entry may be 
      added.
      */
      
      leaf api-type-description {
        type string;
        description
          "Description of the API type used to interact with the
          hosting environment.";
      }
      
      leaf api-version {
        type string;
        description
          "Version of the API used to interact with the hosting 
          environment.";
      }
      
      leaf date-time-created {
        type yang:date-and-time;
        description
          "The system date and time when the VNF catalog entry was
           created in the hosting environment. Eg. when the VNF
           package was onboarded on the NFV Management and 
           Orchestration (MANO)";
      }
      
    }
    container consuming-entities
    {
      description
        "Provides additional information that can be used by consumers
        and planners to determine which entities can use the VNF.";
      
      container compatible-consumers{
         description
           "Entites that can use or interact with the VNF.";
        
         list consumer {
           key "consumer-type consumer-component";
           description
             "List of which entites can use or interact with the 
             VNF.";
      
           leaf consumer-type {
             type bbf-yang:string-ascii64;
             description 
               "Types of applicable consumers. E.g., BAA layer, 
               Access SDN M&C";
           }
           leaf consumer-component {
             type bbf-yang:string-ascii64;
             description 
               "Types of applicable consumers components. E.g., 
               pOLT, uS, SBI adapter, NBI protocol adapter.";
           }
         }
      }
    }
    leaf usage {
      type string;
      description
        "Usage fo the network function. E.g., adaptation, 
        encapsulation, protocol entity";
    }
    
  }
  
  augment '/baa-network-manager:network-manager/' 
    + 'bbf-baa-nfstate:network-functions-state/'
    + 'bbf-baa-nfstate:virtual-network-function-instance' {
    
    description 
      "Extensions to Virtual Network Function (VNF) instances.";
    
    leaf admin-state {
      type bbf-node-types:admin-state;
      description
        "The management administrative state of the VNF instance.";
    }
    leaf admin-state-last-changed {
      type yang:date-and-time;
      description
        "The system date and time when the administrative state of the 
        VNF instance was last changed.";
    }
    leaf oper-state {
      type enumeration {
        enum down {
          description
            "The operational state of the VNF instance is down and
             it is non-operational.";
        }
        enum up {
          description
            "The operational state of the VNF instance is up and
             it is operational.";
        }
      }
      description
        "The operational state of the VNF instance.";
    }
    leaf oper-state-last-changed {
      type yang:date-and-time;
      description
        "The system date and time when the operational state of the 
        VNF instance was last changed.";
    }
    
  }

}
