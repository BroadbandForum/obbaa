module bbf-voltmf-message-monitor {
  yang-version 1.1;
  namespace "urn:bbf:yang:bbf-voltmf-message-monitor";
  prefix bbf-voltmf-msg-mon;
  
  import bbf-yang-types {
    prefix bbf-yang;
  }

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     WA Director: George Dobrowski, Morris Creek Consulting

     WA Director: Bruno Cornaglia, Vodafone";
  description
    "This module contains a collection of YANG definitions needed to
     monitor the virtual OLT management function(vOLTMF) message 
     interactions between the vOLTMF and vOMCI function as described 
     in TR-451.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2021-08-19 {
    description
      "Initial revision.";
    reference
      "TR-451: Section 5.6 vOLT Management Function Description
               Section 5.7 vOLTMF to vOMCI Function Interface";
  }
  

  // Groupings
  grouping voltmf-msg-statistics-grouping {
    description
      "Top-level grouping for monitoring vOLTMF to vOMCI function 
       messages.";
    leaf in-messages {
      type bbf-yang:performance-counter64;
      config false;
      description
        "The number of messages that have been sent by the entity.";
    }
    leaf out-messages {
      type bbf-yang:performance-counter64;
      config false;
      description
        "The number of messages that have been transmitted by the 
         entity.";
    }
    leaf messages-errors {
      type bbf-yang:performance-counter64;
      config false;
      description
        "The number of messages that have had errors.";
    }
  }
}
