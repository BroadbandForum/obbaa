module bbf-obbaa-module-library-check {
    yang-version 1.1;
    namespace "urn:bbf:yang:obbaa:module-library-check";
    prefix baa-modulelibcheck;

    import ietf-yang-library {
        prefix yanglib;
        revision-date 2016-06-21;
    }

    import bbf-obbaa-network-manager {
        prefix network-manager;
    }

    organization
      "Broadband Forum <https://www.broadband-forum.org>";

    contact
      "Comments or questions about this Broadband Forum YANG module
       should be directed to <mailto:obbaa-leaders@broadband-forum.org>.
      ";

    description
      "This module contains a collection of YANG definitions for
       supporting the associations between the BAA layer's instances
       of Device Adapters, the BAA layer's YANG modules and the instances
       devices that are using a Device Adapter.
       
       Copyright 2018-2019 Broadband Forum
       
       Licensed under the Apache License, Version 2.0 (the \"License\");
       you may not use this file except in compliance with the License.
       You may obtain a copy of the License at
       
       http://www.apache.org/licenses/LICENSE-2.0
       Unless required by applicable law or agreed to in writing, software
       distributed under the License is distributed on an \"AS IS\" BASIS,
       WITHOUT WARRANTIES OR CONDITIONS OF ANY KIND, either express or implied.
       See the License for the specific language governing permissions and
       limitations under the License.
      ";

    revision 2018-11-07 {
        description
          "Initial revision.";
        reference
          "OB-BAA User Documentation
             <https://obbaa-broadband-forum.org>";
    }

    grouping devices {
        description
          "This grouping contains a list of devices.";
        leaf device-count {
            type uint32;
            description
              "Total number of devices.";
        }
        container devices {
            description
              "This container contains a list of devices.";
            list device {
                key "name";
                description
                  "A list of devices.";
                leaf name {
                    type leafref {
                        path '/network-manager:network-manager/network-manager:managed-devices/network-manager:device/network-manager:name';
                    }
                    description
                      "A reference to device name";
                }
            }
        }
    }

    grouping device-adapter-list {
        description
          "This grouping contains a list of adapters.";
        list device-adapter {
            key "type interface-version model vendor";
            description
              "List of device adapters and the adapter's associated device.
               A device-adapter is uniquely identified by its type, version,
               model and vendor.
	       ";

            uses network-manager:device-details;

            /* List of devices used by the device adapter */
            uses devices;
        }
    }
    grouping yang-module {
        description
          "This grouping defines two key leaf which can make a yang module unique.";
        leaf name {
            type leafref {
                path '/yanglib:modules-state/yanglib:module/yanglib:name';
            }

            config false;
            description
              "A reference to yang module name";
        }
        leaf revision {
            type leafref {
                path '/yanglib:modules-state/yanglib:module/yanglib:revision';
            }
            config false;
            description
              "A reference to yang module revision";
        }
    }

    container in-use-library-modules {
        config false;
        description
          "The list of YANG modules that are currently in use and the adapters which contains them.
          ";

        list module {
            key "name revision";
            description
              "A list of yang modules which is inuse";
            uses yang-module;

            container associated-adapters {
                description
                  "The device adapters that have indicated support
                   for the module.";
                uses device-adapter-list;
            }
        }
    }

    container device-library-modules {
        config false;
        description
          "This is a representation of the library modules that are used
           by a device.
          ";

        container related-adapter {
            description
              "The adapter info based on which the device was created";
            uses network-manager:device-details;
        }
        container in-use-library-modules {
            description
              "All the yang modules corresponding to the configurations of the device";
            list module {
                key "name revision";
                description
                  "The module list which corresponding to the configurations of the device";
                uses yang-module;
            }
        }
    }
}
