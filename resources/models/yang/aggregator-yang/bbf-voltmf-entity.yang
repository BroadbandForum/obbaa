module bbf-voltmf-entity {
  yang-version 1.1;
  namespace "urn:bbf:yang:bbf-voltmf-entity";
  prefix bbf-voltmf-ent;

  import bbf-yang-types {
    prefix bbf-yang;
  }

  import bbf-vomci-types {
    prefix bbf-vomcit;
  }

  import bbf-vomci-network-function-endpoint-filter {
    prefix bbf-vomci-nf-epf;
  }

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     WA Director: George Dobrowski, Morris Creek Consulting

     WA Director: Bruno Cornaglia, Vodafone";
  description
    "This module contains a collection of YANG definitions needed
     for virtual OLT management function (vOLTMF) entity 
     configuration and state attributes as well as notifications 
     needed to support management of ONUs using vOMCI as defined in 
     TR-451.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2021-08-19 {
    description
      "Initial revision.";
    reference
      "TR-451: Section 5.6 vOLT Management Function Description
               Section 5.7 vOLTMF to vOMCI Function Interface";
  }

  // Groupings
  // vOMCI ONU Management information
  grouping vomci-onu-config {
    description
      "The configuration data needed to manage ONUs via vOMCI.";

    leaf use-vomci-management {
      type boolean;
      description
        "When true, use vOMCI to manage the ONU.";
    }
    
    leaf onu-management-chain-selection {
      type bbf-vomcit:onu-management-chain-selection;
      description
        "The option used to determine the ONU management chain.";
    }

    leaf vomci-function {
      type bbf-yang:string-ascii64;
      description
        "The configured vOMCI function type (not instance) that is 
         being used for the ONU.";
    }

    /*
    Workaround: with the current definition, this leaf-list cannot be used.
    At the time of this change, this node is being revised 
    
    leaf-list onu-management-chain {
      type bbf-vomcit:vomci-entity-type;
      ordered-by user;
      description
        "The ordered list of ONU Management Proxy, vOMCI function, 
         vOMCI Proxy and OLT entities to use for this ONU's 
         management. When the ONU Management Proxy is not deployed, 
         the list is ordered from the vOMCI function to the OLT 
         inclusive. If the vomci-function choice is used for the 
         vomci-function-selection then list contains the vOMCI 
         function instance. When the ONU Management Proxy is 
         deployed, the list is ordered with the ONU Management Proxy 
         and then the OLT.";
    }
    */
  }
  
  grouping vomci-function-policy {
    description
      "The policy used to associate an ONU with a list of
       vOMCI function types.";
    list rule {
      key "name";
      description
        "A rule contains a classification of resources that match a 
         criteria. The result is a list of vOMCI function types. The 
         definition is: first match, then stop searching for matches 
         with other rules, obtain the resulting endpoint specified 
         in this rule.";
      leaf name {
        type bbf-yang:string-ascii64;
        description
          "The rule name.";
      }
      leaf priority {
        type uint16 {
          range "1..max";
        }
        description
          "Indicates the priority for applying the match criteria of 
           this rule against the priority of match criteria of other 
           rules in this filter.

           The higher the value, the lower the priority, i.e. 
           priority 1 is the highest priority.";
      }
      container flexible-match {
        uses bbf-vomci-nf-epf:onu-vomci-criteria-grouping;
        description
          "Provides a generic framework to specify match criteria for 
           filters. Specific match criteria shall be provided using 
           augments in a context dependent way, e.g. match criteria 
           can be augmented for ONUs, or in another context match 
           criteria can be augmented for another resource.";
      }
      leaf-list resulting-vomci-function-type {
        type bbf-yang:string-ascii64;
        description
          "The list of vOMCI function type names.";
      }
    }// rule
  }//nf-filter
}
