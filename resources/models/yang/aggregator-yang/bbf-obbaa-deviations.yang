module bbf-obbaa-deviations {
   yang-version 1.1;
   namespace "urn:bbf:yang:obbaa:deviations";
   prefix baa-deviations;

   import bbf-obbaa-network-manager {
      prefix baa-network-manager;
    }
   
   import bbf-obbaa-onu-management {
      prefix baa-onu-management;
    }
   
   organization
     "Broadband Forum <https://www.broadband-forum.org>";

   contact
     "Comments or questions about this Broadband Forum YANG module
      should be directed to <mailto:obbaa-leaders@broadband-forum.org>.
      ";
   
   description
     "This module contains deviations applicable to the current 
      OB-BAA implementation.
      
      Copyright 2021 Broadband Forum
      
      Licensed under the Apache License, Version 2.0 (the \"License\");
      you may not use this file except in compliance with the License.
      You may obtain a copy of the License at
      
      http://www.apache.org/licenses/LICENSE-2.0
      Unless required by applicable law or agreed to in writing, software
      distributed under the License is distributed on an \"AS IS\" BASIS,
      WITHOUT WARRANTIES OR CONDITIONS OF ANY KIND, either express or implied.
      See the License for the specific language governing permissions and
      limitations under the License. 
     ";
    
   revision 2021-11-10 {
      description
        "Initial revision";
      reference
         "https://obbaa.broadband-forum.org/";
   }
   
   
   //deviations on WT-451
   deviation '/baa-network-manager:network-manager/baa-network-manager:managed-devices/'
      + 'baa-network-manager:device/baa-network-manager:device-management/'
      + 'baa-onu-management:onu-config-info/baa-onu-management:vomci-onu-management/'
      + 'baa-onu-management:use-vomci-management'
   {
      description 
         "The 'use-vomci-management' leaf is replaced by 'planned-onu-management-mode'.";
      
      deviate not-supported;
   }
   
   deviation '/baa-network-manager:network-manager/baa-network-manager:managed-devices/'
      + 'baa-network-manager:device/baa-network-manager:device-management/'
      + 'baa-onu-management:onu-config-info/baa-onu-management:vomci-onu-management/'
      + 'baa-onu-management:onu-management-chain-selection'
   {
      description 
         "Only the configured management chain option is available.";
      
      deviate add {
         must ". = 'configured'";  
      }
      deviate add {
         default configured;  
      }
   }
   
   //end of deviations on WT-451

}
