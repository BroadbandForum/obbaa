module bbf-obbaa-netconf-stack {
    yang-version 1.1;
    namespace "urn:bbf:yang:obbaa:netconf-stack";

    prefix ncs;

    import ietf-netconf-notifications {
        prefix ncn;
    }

    organization
        "Broadband Forum <https://www.broadband-forum.org>";

    contact
        "Comments or questions about this Broadband Forum YANG module
        should be directed to <mailto:obbaa-leaders@broadband-forum.org>.";

    description
        "This module contains a collection of YANG definitions for supporting netconf stack notifications.

        Copyright 2018-2019 Broadband Forum

        Licensed under the Apache License, Version 2.0 (the \"License\");
        you may not use this file except in compliance with the License.
        You may obtain a copy of the License at

        http://www.apache.org/licenses/LICENSE-2.0
        Unless required by applicable law or agreed to in writing, software
        distributed under the License is distributed on an \"AS IS\" BASIS,
        WITHOUT WARRANTIES OR CONDITIONS OF ANY KIND, either express or implied.
        See the License for the specific language governing permissions and
        limitations under the License.";

    revision 2019-01-29 {
        description
            "Initial revision.";
        reference
            "broadband_forum";
    }

    augment "/ncn:netconf-config-change/ncn:edit" {
        list changed-leaf {
            anyxml value {
                description
                    "When the operation corresponds with adding or changing the value of aleaf,
                    then:
                    a) The target is the instance-identifier of the node containing the leaf
                    b) The leaf-value provides the new value of the leaf, between html tags
                    identifying the leaf name, in the form <leaf-name>leaf-value</leaf-name>
                    EG. <admin-state>up</admin-state>.";
            }
        }
    }

    augment "/ncn:netconf-config-change/ncn:edit" {
        leaf implied {
            description
                "Optional leaf, provided when the change cannot be
                directly inferred by the payload of an edit-config request.
                For example, deletion of nodes controlled by a when
                condition that ceased to be true.";
                type empty;
        }
    }

    notification netconf-state-change {
        description
            "Generated when the NETCONF server detects that a state data in
            the <running> datastore has changed.";
            list changes {
            description
            "An state record SHOULD be present for each distinct state change
            that the server has detected on the running datastore.";
        leaf target {
            type instance-identifier;
                description
                    "The instance-identifier of the node containing the leaf
                    with a changed value.";
        }

        list changed-leaf {
            key item;

            leaf item {
                type uint8;
            }
            anyxml value {
                description
                    "The new value of the leaf, between xml tags identifying
                    the leaf name. Example: <oper-status>up</oper-status>.";
            }
            } // list changed-leaf
        } // list changes
    } // notification netconf-state-change
} // module netconf-stack
